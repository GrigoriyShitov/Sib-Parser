Class-definitions DEFINITIONS AUTOMATIC TAGS ::=

BEGIN

IMPORTS

	ActiveSetUpdate,
	ActiveSetUpdateComplete,
	ActiveSetUpdateFailure,	
	AssistanceDataDelivery,
	CellChangeOrderFromUTRAN,
	CellChangeOrderFromUTRANFailure,
	CellUpdate,
	CellUpdateConfirm-CCCH,
	CellUpdateConfirm,
	CounterCheck,
	CounterCheckResponse,
	DownlinkDirectTransfer,
	HandoverToUTRANComplete,
	InitialDirectTransfer,
	HandoverFromUTRANCommand-GERANIu,
	HandoverFromUTRANCommand-GSM,
	HandoverFromUTRANCommand-CDMA2000,
	HandoverFromUTRANFailure,
	MBMSAccessInformation,
	MBMSCommonPTMRBInformation,
	MBMSCurrentCellPTMRBInformation,
	MBMSGeneralInformation,
	MBMSModificationRequest,
	MBMSModifiedServicesInformation,
	MBMSNeighbouringCellPTMRBInformation,
	MBMSSchedulingInformation,
	MBMSUnmodifiedServicesInformation,
	MeasurementControl,
	MeasurementControlFailure,
	MeasurementReport,
	PagingType1,
	PagingType2,
	PhysicalChannelReconfiguration,
	PhysicalChannelReconfigurationComplete,
	PhysicalChannelReconfigurationFailure,
	PhysicalSharedChannelAllocation,
	PUSCHCapacityRequest,
	RadioBearerReconfiguration,
	RadioBearerReconfigurationComplete,
	RadioBearerReconfigurationFailure,
	RadioBearerRelease,
	RadioBearerReleaseComplete,
	RadioBearerReleaseFailure,
	RadioBearerSetup,
	RadioBearerSetupComplete,
	RadioBearerSetupFailure,
	RRCConnectionReject,
	RRCConnectionRelease,
	RRCConnectionRelease-CCCH,
	RRCConnectionReleaseComplete,
	RRCConnectionRequest,
	RRCConnectionSetup,
	RRCConnectionSetupComplete,
	RRCStatus,
	SecurityModeCommand,
	SecurityModeComplete,
	SecurityModeFailure,
	SignallingConnectionRelease,
	SignallingConnectionReleaseIndication,
	SystemInformation-BCH,
	SystemInformation-FACH,
	SystemInformationChangeIndication,
	TransportChannelReconfiguration,
	TransportChannelReconfigurationComplete,
	TransportChannelReconfigurationFailure,
	TransportFormatCombinationControl,
	TransportFormatCombinationControlFailure,
	UECapabilityEnquiry,
	UECapabilityInformation,
	UECapabilityInformationConfirm,
	UplinkDirectTransfer,
	UplinkPhysicalChannelControl,
	URAUpdate,
	URAUpdateConfirm,
	URAUpdateConfirm-CCCH,
	UTRANMobilityInformation,
	UTRANMobilityInformationConfirm,
	UTRANMobilityInformationFailure
FROM PDU-definitions

-- User Equipment IEs :
	IntegrityCheckInfo
FROM InformationElements;

--**************************************************************
--
-- BCCH messages sent on BCH
--
--**************************************************************

BCCH-BCH-Message ::= SEQUENCE {
	message				SystemInformation-BCH
}

END


PDU-definitions DEFINITIONS AUTOMATIC TAGS ::=

BEGIN

--**************************************************************
--
-- IE parameter types from other modules
--
--**************************************************************

IMPORTS

-- Core Network IEs :
	CN-DomainIdentity,
	CN-InformationInfo,
	CN-InformationInfo-r6,
	CN-InformationInfoFull,
	NAS-Message,
	PagingRecordTypeID,
	PLMN-Identity,
-- UTRAN Mobility IEs :
	CellIdentity,
	CellIdentity-PerRL-List,
	URA-Identity,
-- User Equipment IEs :
	UE-RadioAccessCapabilityComp-r7,
	UE-RadioAccessCapability-v7xyext,
	UE-RadioAccessCapabBandFDDList2,
	UE-RadioAccessCapabBandFDDList-ext,
	AccessStratumReleaseIndicator,
	ActivationTime,
	C-RNTI,
	CapabilityUpdateRequirement,
	CapabilityUpdateRequirement-r4,
	CapabilityUpdateRequirement-r4-ext,
	CapabilityUpdateRequirement-r5,
	CapabilityUpdateRequirement-r7-ext,
	CellUpdateCause,
	CellUpdateCause-ext,
	CipheringAlgorithm,
	CipheringModeInfo,
	DelayRestrictionFlag,
	DSCH-RNTI,
	E-RNTI,
	EstablishmentCause,
	FailureCauseWithProtErr,
	FailureCauseWithProtErrTrId,
	GroupReleaseInformation,
	H-RNTI,
	UESpecificBehaviourInformation1idle,
	UESpecificBehaviourInformation1interRAT,
	InitialUE-Identity,
	IntegrityProtActivationInfo,
	IntegrityProtectionModeInfo,
	N-308,
	PagingCause,
	PagingRecordList,
	PagingRecord2List-r5,
	ProtocolErrorIndicator,
	ProtocolErrorIndicatorWithMoreInfo,
	RadioFrequencyBandTDDList,
	Rb-timer-indicator,
	RedirectionInfo,
	RedirectionInfo-r6,
	RejectionCause,
	ReleaseCause,
	RF-CapabilityComp,
	RRC-StateIndicator,
	RRC-TransactionIdentifier,
	SecurityCapability,
	START-Value,
	STARTList,
	SystemSpecificCapUpdateReq-v590ext,
	U-RNTI,
	U-RNTI-Short,
	UE-CapabilityContainer-IEs,
	UE-RadioAccessCapability,
	UE-RadioAccessCapability-v370ext,
	UE-RadioAccessCapability-v380ext,
	UE-RadioAccessCapability-v3a0ext,
	UE-RadioAccessCapability-v3g0ext,
	UE-RadioAccessCapability-v4b0ext,
	UE-RadioAccessCapability-v590ext,
	UE-RadioAccessCapability-v5c0ext,
	UE-RadioAccessCapability-v650ext,
	UE-RadioAccessCapability-v680ext,
	UE-RadioAccessCapabilityComp,
	UE-RadioAccessCapabilityComp-ext,
	UE-RadioAccessCapabilityComp2,
	DL-PhysChCapabilityFDD-v380ext,
	UE-ConnTimersAndConstants,
	UE-ConnTimersAndConstants-v3a0ext,
	UE-ConnTimersAndConstants-r5,
	UE-SecurityInformation,
	UE-SecurityInformation2,
	URA-UpdateCause,
	UTRAN-DRX-CycleLengthCoefficient,
	WaitTime,
-- Radio Bearer IEs :
	DefaultConfigIdentity,
	DefaultConfigIdentity-r4,
	DefaultConfigIdentity-r5,
	DefaultConfigIdentity-r6,
	DefaultConfigMode,
	DL-CounterSynchronisationInfo,
	DL-CounterSynchronisationInfo-r5,
	PDCP-ROHC-TargetMode,
	PredefinedConfigIdentity,
	PredefinedConfigStatusList,
	PredefinedConfigStatusListComp,
	PredefinedConfigSetWithDifferentValueTag,
	RAB-Info,
	RAB-Info-r6,
	RAB-Info-Post,
	RAB-InformationList,
	RAB-InformationList-r6,
	RAB-InformationReconfigList,
	RAB-InformationSetupList,
	RAB-InformationSetupList-r4,
	RAB-InformationSetupList-r5,
	RAB-InformationSetupList-r6-ext,
	RAB-InformationSetupList-r6,
	RB-ActivationTimeInfoList,
	RB-COUNT-C-InformationList,
	RB-COUNT-C-MSB-InformationList,
	RB-IdentityList,
	RB-InformationAffectedList,
	RB-InformationAffectedList-r5,
	RB-InformationAffectedList-r6,
	RB-InformationChangedList-r6,
	RB-InformationReconfigList,
	RB-InformationReconfigList-r4,
	RB-InformationReconfigList-r5,
	RB-InformationReconfigList-r6,
	RB-InformationReleaseList,
	RB-PDCPContextRelocationList,
	SRB-InformationSetupList,
	SRB-InformationSetupList-r5,
	SRB-InformationSetupList-r6,
	SRB-InformationSetupList2,
	SRB-InformationSetupList2-r6,
	UL-CounterSynchronisationInfo,
-- Transport Channel IEs:
	CPCH-SetID,
	DL-AddReconfTransChInfo2List,
	DL-AddReconfTransChInfoList,
	DL-AddReconfTransChInfoList-r4,
	DL-AddReconfTransChInfoList-r5,
	DL-CommonTransChInfo,
	DL-CommonTransChInfo-r4,
	DL-DeletedTransChInfoList,
	DL-DeletedTransChInfoList-r5,
	DRAC-StaticInformationList,
	PowerOffsetInfoShort,
	TFC-Subset,
	TFCS-Identity,
	UL-AddReconfTransChInfoList,
	UL-AddReconfTransChInfoList-r6,
	UL-CommonTransChInfo,
	UL-CommonTransChInfo-r4,
	UL-DeletedTransChInfoList,
	UL-DeletedTransChInfoList-r6,
-- Physical Channel IEs :
	Alpha,
	BEACON-PL-Est,
	CCTrCH-PowerControlInfo,
	CCTrCH-PowerControlInfo-r4,
	CCTrCH-PowerControlInfo-r5,
	CCTrCH-PowerControlInfo-r7,
	ConstantValue,
	ConstantValueTdd,
	CPCH-SetInfo,
	DHS-Sync,
	DL-CommonInformation,
	DL-CommonInformation-r4,
	DL-CommonInformation-r5,
	DL-CommonInformation-r6,
	DL-CommonInformation-r7,
	DL-CommonInformationPost,
	DL-HSPDSCH-Information,
	DL-HSPDSCH-Information-r6,
	DL-HSPDSCH-Information-r7,
	DL-InformationPerRL-List,
	DL-InformationPerRL-List-r4,
	DL-InformationPerRL-List-r5,
	DL-InformationPerRL-List-r5bis,
	DL-InformationPerRL-List-r6,
	DL-InformationPerRL-List-r7,
	DL-InformationPerRL-ListPostFDD,
	DL-InformationPerRL-PostTDD,
	DL-InformationPerRL-PostTDD-LCR-r4,
	DL-PDSCH-Information,
	DL-TPC-PowerOffsetPerRL-List,
	DPC-Mode,
	DPCH-CompressedModeStatusInfo,
	DynamicPersistenceLevel,
	E-DCH-ReconfigurationInfo,
	EXT-UL-TimingAdvance,
	FrequencyInfo,
	FrequencyInfoFDD,
	FrequencyInfoTDD,
	HARQ-Preamble-Mode,
	HS-SICH-Power-Control-Info-TDD384,
	HS-SICH-Power-Control-Info-TDD768,
	MaxAllowedUL-TX-Power,
	OpenLoopPowerControl-IPDL-TDD-r4,
	PDSCH-CapacityAllocationInfo,
	PDSCH-CapacityAllocationInfo-r4,
	PDSCH-CapacityAllocationInfo-r7,
	PDSCH-Identity,
	PrimaryCPICH-Info,
	PrimaryCCPCH-TX-Power,
	PUSCH-CapacityAllocationInfo,
	PUSCH-CapacityAllocationInfo-r4,
	PUSCH-CapacityAllocationInfo-r7,
	PUSCH-Identity,
	PUSCH-SysInfoList-HCR-r5,
	PDSCH-SysInfoList-HCR-r5,
	RL-AdditionInformationList,
	RL-AdditionInformationList-r6,
	RL-RemovalInformationList,
	Serving-HSDSCH-CellInformation,
	SpecialBurstScheduling,
	SSDT-Information,
	SSDT-Information-r4,
	TFC-ControlDuration,
	SSDT-UL,
	TimingMaintainedSynchInd,
	TimeslotList,
	TimeslotList-r4,
	TX-DiversityMode,
	UL-ChannelRequirement,
	UL-ChannelRequirement-r4,
	UL-ChannelRequirement-r5,
	UL-ChannelRequirementWithCPCH-SetID,
	UL-ChannelRequirementWithCPCH-SetID-r4,
	UL-ChannelRequirementWithCPCH-SetID-r5,
	UL-DPCH-Info,
	UL-DPCH-Info-r4,
	UL-DPCH-Info-r5,
	UL-DPCH-Info-r6,
	UL-DPCH-Info-r7,
	UL-DPCH-InfoPostFDD,
	UL-DPCH-InfoPostTDD,
	UL-DPCH-InfoPostTDD-LCR-r4,
	UL-EDCH-Information-r6,
	UL-SynchronisationParameters-r4,
	UL-TimingAdvance,
	UL-TimingAdvanceControl,
	UL-TimingAdvanceControl-r4,
	UL-TimingAdvanceControl-r7,
	UL-TimingAdvance-VHCR,
-- Measurement IEs :
	AdditionalMeasurementID-List,
	DeltaRSCP,
	Frequency-Band,
	EventResults,
	Inter-FreqEventCriteriaList-v590ext,
	Intra-FreqEventCriteriaList-v590ext,
	IntraFreqReportingCriteria-1b-r5,
	IntraFreqEvent-1d-r5,
	IntraFreqCellID,
	InterFreqEventResults-LCR-r4-ext,
	InterRATCellInfoIndication,
	InterRAT-TargetCellDescription,
	MeasuredResults,
	MeasuredResults-v390ext,
	MeasuredResults-v590ext,
	MeasuredResultsList,
	MeasuredResultsList-LCR-r4-ext,
	MeasuredResultsOnRACH,
	MeasuredResultsOnRACHinterFreq,
	MeasurementCommand,
	MeasurementCommand-r4,
	MeasurementCommand-r6,
	MeasurementIdentity,
	MeasurementReportingMode,
	PrimaryCCPCH-RSCP,
	SFN-Offset-Validity,
	TimeslotListWithISCP,
	TrafficVolumeMeasuredResultsList,
	UE-Positioning-GPS-AssistanceData,
	UE-Positioning-Measurement-v390ext,
	UE-Positioning-Measurement-v7xyext,
	UE-Positioning-OTDOA-AssistanceData,
	UE-Positioning-OTDOA-AssistanceData-r4ext,
	UE-Positioning-OTDOA-AssistanceData-UEB,
	VelocityEstimate,
	UE-InternalMeasuredResults-r7,
-- Other IEs :
	BCCH-ModificationInfo,
	CDMA2000-MessageList,
	GSM-TargetCellInfoList,
	GERANIu-MessageList,
	GERAN-SystemInformation,
	GSM-MessageList,
	InterRAT-ChangeFailureCause,
	InterRAT-HO-FailureCause,
	InterRAT-UE-RadioAccessCapabilityList,
	InterRAT-UE-RadioAccessCapability-v590ext,
	InterRAT-UE-SecurityCapList,
	IntraDomainNasNodeSelector,
	ProtocolErrorMoreInformation,
	Rplmn-Information,
	Rplmn-Information-r4,
	SegCount,
	SegmentIndex,
	SFN-Prime,
	SIB-Data-fixed,
	SIB-Data-variable,
	SIB-Type,
-- MBMS IEs:
	MBMS-CellGroupIdentity-r6,
	MBMS-CommonRBInformationList-r6,
	MBMS-CurrentCell-SCCPCHList-r6,
	MBMS-JoinedInformation-r6,
	MBMS-MICHConfigurationInfo-r6,
	MBMS-MICHConfigurationInfo-r7,
	MBMS-ModifedServiceList-r6,
	MBMS-MSCH-ConfigurationInfo-r6,
	MBMS-NeighbouringCellSCCPCHList-r6,
	MBMS-NumberOfNeighbourCells-r6,
	MBMS-PhyChInformationList-r6,
	MBMS-PL-ServiceRestrictInfo-r6,
	MBMS-PreferredFreqRequest-r6,
	MBMS-PreferredFrequencyList-r6,
	MBMS-PTMActivationTime-r6,
	MBMS-ServiceAccessInfoList-r6,
	MBMS-ServiceIdentity-r6,
	MBMS-ServiceSchedulingInfoList-r6,
	MBMS-SIBType5-SCCPCHList-r6,
	MBMS-TimersAndCounters-r6,
	MBMS-TranspChInfoForEachCCTrCh-r6,
	MBMS-TranspChInfoForEachTrCh-r6,
	MBMS-UnmodifiedServiceList-r6
FROM InformationElements

	maxSIBperMsg,
	maxURNTI-Group
FROM Constant-definitions;

-- ***************************************************
--
-- SYSTEM INFORMATION for BCH
--
-- ***************************************************

SystemInformation-BCH ::= SEQUENCE {
	-- Other information elements
		sfn-Prime						SFN-Prime,
		payload 						CHOICE {
			noSegment						NULL,
			firstSegment					FirstSegment,
			subsequentSegment				SubsequentSegment,
			lastSegmentShort						LastSegmentShort,
			lastAndFirst					SEQUENCE {
				lastSegmentShort				LastSegmentShort,
				firstSegment					FirstSegmentShort
			},
			lastAndComplete					SEQUENCE {
				lastSegmentShort				LastSegmentShort,
				completeSIB-List				CompleteSIB-List
			},
			lastAndCompleteAndFirst			SEQUENCE {
				lastSegmentShort				LastSegmentShort,
				completeSIB-List				CompleteSIB-List,
				firstSegment					FirstSegmentShort
			},
			completeSIB-List				CompleteSIB-List,
			completeAndFirst				SEQUENCE {
				completeSIB-List				CompleteSIB-List,
				firstSegment					FirstSegmentShort
			},
			completeSIB						CompleteSIB,
			lastSegment						LastSegment,
			spare5							NULL,
			spare4							NULL,
			spare3							NULL,
			spare2							NULL,
			spare1							NULL
		}
}

SFN-Prime ::=						INTEGER (0..2047)

-- ***************************************************
--
-- First segment
--
-- ***************************************************

FirstSegment ::=					SEQUENCE {
	-- Other information elements
		sib-Type						SIB-Type,
		seg-Count						SegCount,
		sib-Data-fixed					SIB-Data-fixed
}

-- ***************************************************
--
-- Subsequent segment
--
-- ***************************************************

SubsequentSegment ::=				SEQUENCE {
	-- Other information elements
		sib-Type						SIB-Type,
		segmentIndex					SegmentIndex,
		sib-Data-fixed					SIB-Data-fixed
}

-- ***************************************************
--
-- Last segment
--
-- ***************************************************

LastSegment ::=						SEQUENCE {
	-- Other information elements
		sib-Type						SIB-Type,
		segmentIndex					SegmentIndex,
		-- For sib-Data-fixed, in case the SIB data is less than 222 bits, padding
		-- shall be used. The same padding bits shall be used as defined in clause 12.1
		sib-Data-fixed					SIB-Data-fixed
}

LastSegmentShort ::=						SEQUENCE {
	-- Other information elements
		sib-Type						SIB-Type,
		segmentIndex					SegmentIndex,
		sib-Data-variable				SIB-Data-variable
}

-- ***************************************************
--
-- First segment (short)
--
-- ***************************************************

FirstSegmentShort ::=				SEQUENCE {
	-- Other information elements
		sib-Type						SIB-Type,
		seg-Count						SegCount,
		sib-Data-variable				SIB-Data-variable
}

-- ***************************************************
--
-- Complete SIB
--
-- ***************************************************

CompleteSIB-List ::=				SEQUENCE (SIZE (1..maxSIBperMsg)) OF
										CompleteSIBshort

CompleteSIB ::=						SEQUENCE {
	-- Other information elements
		sib-Type						SIB-Type,
		-- For sib-Data-fixed, in case the SIB data is less than 226 bits, padding
		-- shall be used. The same padding bits shall be used as defined in clause 12.1
		sib-Data-fixed					BIT STRING (SIZE (226))
}

CompleteSIBshort ::=						SEQUENCE {
	-- Other information elements
		sib-Type						SIB-Type,
		sib-Data-variable				SIB-Data-variable
}

END






InformationElements DEFINITIONS AUTOMATIC TAGS ::=

-- ***************************************************
--
--     CORE NETWORK INFORMATION ELEMENTS (10.3.1)
--
-- ***************************************************

BEGIN

IMPORTS

	hiPDSCHidentities,
	hiPUSCHidentities,
	hiRM,
	maxAC,
	maxAdditionalMeas,
	maxASC,
	maxASCmap,
	maxASCpersist,
	maxCCTrCH,
	maxCellMeas,
	maxCellMeas-1,
	maxCNdomains,
	maxCPCHsets,
	maxDPCH-DLchan,
	maxDPDCH-UL,
	maxDRACclasses,
	maxE-DCHMACdFlow,
	maxE-DCHMACdFlow-1,
	maxFACHPCH,
	maxFreq,
	maxFreqBandsFDD,
	maxFreqBandsFDD-ext,
	maxFreqBandsTDD,
	maxFreqBandsGSM,
	maxGERAN-SI,
	maxHProcesses,
	maxHSDSCHTBIndex,
	maxHSDSCHTBIndex-tdd384,
	maxHSSCCHs,
	maxInterSysMessages,
	maxLoCHperRLC,
	maxMAC-d-PDUsizes,
	maxMBMS-CommonCCTrCh,
	maxMBMS-CommonPhyCh,
	maxMBMS-CommonRB,
	maxMBMS-CommonTrCh,
	maxMBMS-Freq,
	maxMBMS-L1CP,
	maxMBMSservCount,
	maxMBMSservModif,
	maxMBMSservSched,
	maxMBMSservUnmodif,
	maxMBMSTransmis,
	maxMeasEvent,
	maxMeasIntervals,
	maxMeasParEvent,
	maxNumCDMA2000Freqs,
	maxNumFDDFreqs,
	maxNumGSMFreqRanges,
	maxGSMTargetCells,
	maxNumTDDFreqs,
	maxOtherRAT,
	maxOtherRAT-16,
	maxPage1,
	maxPCPCH-APsig,
	maxPCPCH-APsubCh,
	maxPCPCH-CDsig,
	maxPCPCH-CDsubCh,
	maxPCPCH-SF,
	maxPCPCHs,
	maxPDCPAlgoType,
	maxPDSCH,
	maxPDSCH-TFCIgroups,
	maxPRACH,
	maxPRACH-FPACH,
	maxPredefConfig,
	maxPUSCH,
	maxQueueIDs,
	maxRABsetup,
	maxRAT,
	maxRB,
	maxRBallRABs,
	maxRBperTrCh,
	maxRBMuxOptions,
	maxRBperRAB,
	maxReportedGSMCells,
	maxRLCPDUsizePerLogChan,
	maxSRBsetup,
	maxRL,
	maxRL-1,
	maxEDCHRL,
	maxROHC-PacketSizes-r4,
	maxROHC-Profile-r4,
	maxSCCPCH,
	maxSat,
	maxSIB,
	maxSIB-FACH,
	maxSystemCapability,
	maxTF,
	maxTF-CPCH,
	maxTFC,
	maxTFCsub,
	maxTFCI-2-Combs,
	maxTGPS,
	maxTrCH,
	maxTrCHpreconf,
	maxTS,
	maxTS-1,
	maxTS-2,
	maxTS-LCR,
	maxTS-LCR-1,
	maxURA,
	maxURNTI-Group
FROM Constant-definitions;

Ansi-41-IDNNS ::=							BIT STRING (SIZE (14))

SIB-Type ::=						ENUMERATED {
										masterInformationBlock,
										systemInformationBlockType1,
										systemInformationBlockType2,
										systemInformationBlockType3,
										systemInformationBlockType4,
										systemInformationBlockType5,
										systemInformationBlockType6,
										systemInformationBlockType7,
		-- dummy, dummy2 and dummy3 are not used in this version of the specification,
		-- they should not be sent. If they are received the UE behaviour is not specified.
										dummy,
										dummy2,
										dummy3,
										systemInformationBlockType11,
										systemInformationBlockType12,
										systemInformationBlockType13,
										systemInformationBlockType13-1,
										systemInformationBlockType13-2,
										systemInformationBlockType13-3,
										systemInformationBlockType13-4,
										systemInformationBlockType14,
										systemInformationBlockType15,
										systemInformationBlockType15-1,
										systemInformationBlockType15-2,
										systemInformationBlockType15-3,
										systemInformationBlockType16,
										systemInformationBlockType17,
										systemInformationBlockType15-4,
										systemInformationBlockType18,
										schedulingBlock1,
										schedulingBlock2,
										systemInformationBlockType15-5,
										systemInformationBlockType5bis, 
										spare1 }


SIB-TypeAndTag ::=					CHOICE {
	sysInfoType1						PLMN-ValueTag,
	sysInfoType2						CellValueTag,
	sysInfoType3						CellValueTag,
	sysInfoType4						CellValueTag,
	sysInfoType5						CellValueTag,
	sysInfoType6						CellValueTag,
	sysInfoType7						NULL,
	-- dummy, dummy2 and dummy3 are not used in this version of the specification,
	-- they should not be sent. If they are received the UE behaviour is not specified.
	dummy								CellValueTag,
	dummy2								NULL,
	dummy3								NULL,
	sysInfoType11						CellValueTag,
	sysInfoType12 						CellValueTag,
	sysInfoType13						CellValueTag,
	sysInfoType13-1						CellValueTag, 
	sysInfoType13-2						CellValueTag,
	sysInfoType13-3						CellValueTag,
	sysInfoType13-4						CellValueTag,
	sysInfoType14						NULL,
	sysInfoType15						CellValueTag,
	sysInfoType16						PredefinedConfigIdentityAndValueTag,
	sysInfoType17						NULL,
	sysInfoType15-1						CellValueTag,
	sysInfoType15-2						SIBOccurrenceIdentityAndValueTag,
	sysInfoType15-3						SIBOccurrenceIdentityAndValueTag,
	sysInfoType15-4						CellValueTag,
	sysInfoType18						CellValueTag,
	sysInfoType15-5						CellValueTag,
	sysInfoType5bis						CellValueTag,
	spare4								NULL,
	spare3								NULL,
	spare2								NULL,
	spare1								NULL
}

SIBSb-TypeAndTag ::=					CHOICE {
	sysInfoType1						PLMN-ValueTag,
	sysInfoType2						CellValueTag,
	sysInfoType3						CellValueTag,
	sysInfoType4						CellValueTag,
	sysInfoType5						CellValueTag,
	sysInfoType6						CellValueTag,
	sysInfoType7						NULL,
	-- dummy, dummy2 and dummy3 are not used in this version of the specification,
	-- they should not be sent. If they are received the UE behaviour is not specified.
	dummy								CellValueTag,
	dummy2								NULL,
	dummy3								NULL,
	sysInfoType11						CellValueTag,
	sysInfoType12 						CellValueTag,
	sysInfoType13						CellValueTag,
	sysInfoType13-1						CellValueTag, 
	sysInfoType13-2						CellValueTag,
	sysInfoType13-3						CellValueTag,
	sysInfoType13-4						CellValueTag,
	sysInfoType14						NULL,
	sysInfoType15						CellValueTag,
	sysInfoType16						PredefinedConfigIdentityAndValueTag,
	sysInfoType17						NULL,
	sysInfoTypeSB1						CellValueTag,
	sysInfoTypeSB2						CellValueTag,
	sysInfoType15-1						CellValueTag,
	sysInfoType15-2						SIBOccurrenceIdentityAndValueTag,
	sysInfoType15-3						SIBOccurrenceIdentityAndValueTag,
	sysInfoType15-4						CellValueTag,
	sysInfoType18						CellValueTag,
	sysInfoType15-5						CellValueTag,
	sysInfoType5bis						CellValueTag,
	spare2								NULL,
	spare1								NULL
}

SibOFF ::=							ENUMERATED {
										so2, so4, so6, so8, so10,
										so12, so14, so16, so18,
										so20, so22, so24, so26,
										so28, so30, so32 }

SibOFF-List ::=						SEQUENCE (SIZE (1..15)) OF
										SibOFF

SysInfoType1 ::=					SEQUENCE {
	-- Core network IEs
		cn-CommonGSM-MAP-NAS-SysInfo	NAS-SystemInformationGSM-MAP,	
		cn-DomainSysInfoList			CN-DomainSysInfoList,
	-- User equipment IEs
		ue-ConnTimersAndConstants		UE-ConnTimersAndConstants			OPTIONAL,
		ue-IdleTimersAndConstants		UE-IdleTimersAndConstants			OPTIONAL,
	-- Extension mechanism for non- release99 information
		v3a0NonCriticalExtensions		SEQUENCE {
			sysInfoType1-v3a0ext		SysInfoType1-v3a0ext-IEs,
			nonCriticalExtensions		SEQUENCE {} OPTIONAL
		}							OPTIONAL
}

SysInfoType1-v3a0ext-IEs ::= SEQUENCE {
	ue-ConnTimersAndConstants-v3a0ext		UE-ConnTimersAndConstants-v3a0ext,
	ue-IdleTimersAndConstants-v3a0ext		UE-IdleTimersAndConstants-v3a0ext
}

SysInfoType2 ::=					SEQUENCE {
	-- UTRAN mobility IEs
		ura-IdentityList				URA-IdentityList,
	-- Extension mechanism for non- release99 information
		nonCriticalExtensions			SEQUENCE {}							OPTIONAL
}

SysInfoType3 ::=					SEQUENCE {
		sib4indicator					BOOLEAN,
	-- UTRAN mobility IEs
		cellIdentity					CellIdentity,
		cellSelectReselectInfo			CellSelectReselectInfoSIB-3-4,
		cellAccessRestriction			CellAccessRestriction,
	-- Extension mechanism for non- release99 information
		v4b0NonCriticalExtensions		SEQUENCE { 
			sysInfoType3-v4b0ext			SysInfoType3-v4b0ext-IEs,
			v590NonCriticalExtension		SEQUENCE {
				sysInfoType3-v590ext			SysInfoType3-v590ext,
				v5c0NoncriticalExtension		SEQUENCE {
					sysInfoType3-v5c0ext			SysInfoType3-v5c0ext-IEs,
					v670NonCriticalExtension			SEQUENCE {
						sysInfoType3-v670ext				SysInfoType3-v670ext,
						nonCriticalExtensions			SEQUENCE {}						OPTIONAL
					}							OPTIONAL
				}							OPTIONAL
			} 							OPTIONAL
		}							OPTIONAL
}

SysInfoType3-v4b0ext-IEs ::= SEQUENCE {
	mapping-LCR						Mapping-LCR-r4							OPTIONAL
}

SysInfoType3-v590ext ::= SEQUENCE {
	cellSelectReselectInfo-v590ext		CellSelectReselectInfo-v590ext 		OPTIONAL
}

SysInfoType3-v5c0ext-IEs ::= SEQUENCE {
	cellSelectReselectInfoTreselectionScaling-v5c0ext
										CellSelectReselectInfoTreselectionScaling-v5c0ext	OPTIONAL
}

SysInfoType3-v670ext ::= SEQUENCE {
	 	domainSpecificAccessRestrictionParametersForPLMNOfMIB
									DomainSpecificAccessRestrictionParam-v670ext	OPTIONAL,
		domainSpecificAccessRestictionForSharedNetwork
									DomainSpecificAccessRestrictionForSharedNetwork-v670ext	OPTIONAL
}

SysInfoType4 ::=					SEQUENCE {
	-- UTRAN mobility IEs
		cellIdentity					CellIdentity,
		cellSelectReselectInfo			CellSelectReselectInfoSIB-3-4,
		cellAccessRestriction			CellAccessRestriction,
	-- Extension mechanism for non- release99 information
		v4b0NonCriticalExtensions		SEQUENCE { 
			sysInfoType4-v4b0ext			SysInfoType4-v4b0ext-IEs,
			v590NonCriticalExtension		SEQUENCE {
				sysInfoType4-v590ext			SysInfoType4-v590ext,
				v5b0NonCriticalExtension		SEQUENCE {
					sysInfoType4-v5b0ext			SysInfoType4-v5b0ext-IEs,
					v5c0NonCriticalExtension			SEQUENCE {
						sysInfoType4-v5c0ext				SysInfoType4-v5c0ext-IEs,
						nonCriticalExtensions			SEQUENCE {}						OPTIONAL
					}	OPTIONAL
				}	OPTIONAL
			}	OPTIONAL
		}	OPTIONAL
}

SysInfoType4-v4b0ext-IEs ::= SEQUENCE {
	mapping-LCR						Mapping-LCR-r4							OPTIONAL
}


SysInfoType4-v590ext ::= SEQUENCE {
	cellSelectReselectInfo-v590ext		CellSelectReselectInfo-v590ext 		OPTIONAL
}

SysInfoType4-v5b0ext-IEs ::= SEQUENCE {
	cellSelectReselectInfoPCHFACH-v5b0ext	CellSelectReselectInfoPCHFACH-v5b0ext 		OPTIONAL
}

SysInfoType4-v5c0ext-IEs ::= SEQUENCE {
	cellSelectReselectInfoTreselectionScaling-v5c0ext
										CellSelectReselectInfoTreselectionScaling-v5c0ext	OPTIONAL
}

SysInfoType5 ::=					SEQUENCE {
		sib6indicator					BOOLEAN,
	-- Physical channel IEs
		pich-PowerOffset				PICH-PowerOffset,
		modeSpecificInfo				CHOICE {
			fdd								SEQUENCE {
				aich-PowerOffset				AICH-PowerOffset
			},
			tdd								SEQUENCE {
	-- If PDSCH/PUSCH is configured for 1.28Mcps TDD, the following IEs should be absent
	--   and the info included in the tdd128SpecificInfo instead.
	-- If PDSCH/PUSCH is configured for 3.84Mcps TDD in R5, HCR-r5-SpecificInfo should also be 
	-- included. 
				pusch-SysInfoList-SFN			PUSCH-SysInfoList-SFN		OPTIONAL,
				pdsch-SysInfoList-SFN			PDSCH-SysInfoList-SFN		OPTIONAL,
				openLoopPowerControl-TDD		OpenLoopPowerControl-TDD
			}
		},
		primaryCCPCH-Info				PrimaryCCPCH-Info					OPTIONAL,
		prach-SystemInformationList		PRACH-SystemInformationList,
		sCCPCH-SystemInformationList	SCCPCH-SystemInformationList,
		-- cbs-DRX-Level1Information is conditional on any of the CTCH indicator IEs in
		-- sCCPCH-SystemInformationList
		cbs-DRX-Level1Information		CBS-DRX-Level1Information			OPTIONAL,
	-- Extension mechanism for non- release99 information
		v4b0NonCriticalExtensions		SEQUENCE {
			sysInfoType5-v4b0ext			SysInfoType5-v4b0ext-IEs		OPTIONAL,
		-- Extension mechanism for non- rel-4 information
			v590NonCriticalExtensions		SEQUENCE {
				sysInfoType5-v590ext			SysInfoType5-v590ext-IEs		OPTIONAL,
				v650NonCriticalExtensions		SEQUENCE {
					sysInfoType5-v650ext			SysInfoType5-v650ext-IEs		OPTIONAL,
					v680NonCriticalExtensions		SEQUENCE {
						sysInfoType5-v680ext			SysInfoType5-v680ext-IEs		OPTIONAL,
						v690NonCriticalExtensions		SEQUENCE {
							sysInfoType5-v690ext			SysInfoType5-v690ext-IEs,
							v7xyNonCriticalExtensions		SEQUENCE {
								sysInfoType5-v7xyext			SysInfoType5-v7xyext-IEs,
								nonCriticalExtensions			SEQUENCE {}				OPTIONAL
							}		OPTIONAL
						}		OPTIONAL
					}		OPTIONAL
				}		OPTIONAL
			}		OPTIONAL
		}		OPTIONAL
}

SysInfoType5-v4b0ext-IEs ::= SEQUENCE {
	--The following IE PNBSCH-Allocation-r4 shall be used for 3.84Mcps TDD only.
	pNBSCH-Allocation-r4 			PNBSCH-Allocation-r4			OPTIONAL,
	-- In case of TDD, the following IE is included instead of the
	-- IE up-IPDL-Parameter in up-OTDOA-AssistanceData.
	openLoopPowerControl-IPDL-TDD	OpenLoopPowerControl-IPDL-TDD-r4	OPTIONAL,
-- If SysInfoType5 is sent to describe a 1.28Mcps TDD cell, the IE PRACH-RACH-Info included in
-- PRACH-SystemInformationList shall be ignored, the IE PRACH-Partitioning and the 
-- IE rach-TransportFormatSet shall be absent and the corresponding IE in the following 
-- PRACH-SystemInformationList-LCR-r4 shall be used
	prach-SystemInformationList-LCR-r4	PRACH-SystemInformationList-LCR-r4	OPTIONAL, 
	tdd128SpecificInfo				SEQUENCE {
		pusch-SysInfoList-SFN			PUSCH-SysInfoList-SFN-LCR-r4	OPTIONAL,
		pdsch-SysInfoList-SFN			PDSCH-SysInfoList-SFN-LCR-r4	OPTIONAL,
		pCCPCH-LCR-Extensions			PrimaryCCPCH-Info-LCR-r4-ext	OPTIONAL,
		sCCPCH-LCR-ExtensionsList		SCCPCH-SystemInformationList-LCR-r4-ext
	}																OPTIONAL,
	frequencyBandIndicator			RadioFrequencyBandFDD			OPTIONAL
}

SysInfoType5-v590ext-IEs ::= SEQUENCE {
	hcr-r5-SpecificInfo				SEQUENCE {
		pusch-SysInfoList-SFN			PUSCH-SysInfoList-SFN-HCR-r5	OPTIONAL,
		pdsch-SysInfoList-SFN			PDSCH-SysInfoList-SFN-HCR-r5	OPTIONAL
	}																	OPTIONAL
}

SysInfoType5-v650ext-IEs ::= SEQUENCE {
	frequencyBandIndicator2			RadioFrequencyBandFDD2
}

SysInfoType5-v680ext-IEs ::= SEQUENCE {
	-- TABULAR: HSDPA Cell Indicator is MD in tabular description
	-- Default value is ’HSDPA Capability not indicated’
	hsdpa-CellIndicator		ENUMERATED { hsdpa-CapableCell }			OPTIONAL
}

SysInfoType5-v690ext-IEs ::=		SEQUENCE {
	-- TABULAR: E-DCH Cell Indicator is MD in tabular description
	-- Default value is ’E-DCH Capability not indicated’
	edch-CellIndicator					ENUMERATED { edch-CapableCell }		OPTIONAL,
	sccpch-SystemInformation-MBMS		CHOICE {
		mcchOnSCCPCHusedForNonMBMS			MBMS-MCCH-ConfigurationInfo-r6,
		mcchOnSCCPCHusedOnlyForMBMS			SCCPCH-SystemInformation-MBMS-r6
	}		OPTIONAL,
	additionalPRACH-TF-and-TFCS-CCCH-List	AdditionalPRACH-TF-and-TFCS-CCCH-List	OPTIONAL,
	cBS-DRX-Level1Information-extension		CBS-DRX-Level1Information-extension-r6	OPTIONAL
}

SysInfoType5-v7xyext-IEs ::=		SEQUENCE {
	pusch-SysInfoList-SFN-VHCR			PUSCH-SysInfoList-SFN-VHCR		OPTIONAL,
	prach-SystemInformationList-r7		PRACH-SystemInformationList-r7	OPTIONAL,
	pdsch-SysInfoList-SFN-r7			PDSCH-SysInfoList-r7			OPTIONAL,
	sccpch-SystemInformation-MBMS		CHOICE {
		mcchOnSCCPCHusedForNonMBMS			MBMS-MCCH-ConfigurationInfo-r6,
		mcchOnSCCPCHusedOnlyForMBMS			SCCPCH-SystemInformation-MBMS-r7
	}		OPTIONAL,
	sCCPCH-SystemInformationList-r7		SCCPCH-SystemInformationList-r7	OPTIONAL
}


-- SysInfoType5bis uses the same structure as SysInfoType5
SysInfoType5bis ::= SysInfoType5

SysInfoType6 ::=					SEQUENCE {
	-- Physical channel IEs
		pich-PowerOffset				PICH-PowerOffset,
		modeSpecificInfo				CHOICE {
			fdd								SEQUENCE {
				aich-PowerOffset				AICH-PowerOffset,
				-- dummy is not used in this version of specification, it should
				-- not be sent and if received it should be ignored.
				dummy							CSICH-PowerOffset			OPTIONAL
			},
			tdd								SEQUENCE {
				-- If PDSCH/PUSCH is configured for 1.28Mcps TDD, pusch-SysInfoList-SFN,
				-- pdsch-SysInfoList-SFN and openLoopPowerControl-TDD should be absent
				-- and the info included in the tdd128SpecificInfo instead.
				-- If PDSCH/PUSCH is configured for 3.84Mcps TDD in R5, HCR-r5-SpecificInfo should 
				-- also be included.
				pusch-SysInfoList-SFN			PUSCH-SysInfoList-SFN		OPTIONAL,
				pdsch-SysInfoList-SFN			PDSCH-SysInfoList-SFN		OPTIONAL,
				openLoopPowerControl-TDD		OpenLoopPowerControl-TDD
			}
		},
		primaryCCPCH-Info				PrimaryCCPCH-Info					OPTIONAL,
		prach-SystemInformationList		PRACH-SystemInformationList			OPTIONAL,
		sCCPCH-SystemInformationList	SCCPCH-SystemInformationList		OPTIONAL,
		cbs-DRX-Level1Information		CBS-DRX-Level1Information			OPTIONAL,
		-- Conditional on any of the CTCH indicator IEs in
		-- sCCPCH-SystemInformationList
	-- Extension mechanism for non- release99 information
		v4b0NonCriticalExtensions		SEQUENCE {
			sysInfoType6-v4b0ext			SysInfoType6-v4b0ext-IEs		OPTIONAL,
		-- Extension mechanism for non- rel-4 information
			v590NonCriticalExtensions	SEQUENCE {
				sysInfoType6-v590ext			SysInfoType6-v590ext-IEs		OPTIONAL,
				v650nonCriticalExtensions		SEQUENCE {
					sysInfoType6-v650ext			SysInfoType6-v650ext-IEs		OPTIONAL,
					v690nonCriticalExtensions		SEQUENCE {
						sysInfoType6-v690ext			SysInfoType6-v690ext-IEs,
						v7xyNonCriticalExtensions		SEQUENCE {
							sysInfoType6-v7xyext			SysInfoType6-v7xyext-IEs,
							nonCriticalExtensions			SEQUENCE {}					OPTIONAL
						}	OPTIONAL
					}							OPTIONAL
				}							OPTIONAL
			}							OPTIONAL
		}							OPTIONAL
}

SysInfoType6-v4b0ext-IEs ::= SEQUENCE {
	-- openLoopPowerControl-IPDL-TDD is present only if IPDLs are applied for TDD
	openLoopPowerControl-IPDL-TDD	OpenLoopPowerControl-IPDL-TDD-r4	OPTIONAL,
	-- If SysInfoType6 is sent to describe a 1.28Mcps TDD cell, the IE PRACH-RACH-Info included
	-- in PRACH-SystemInformationList shall be ignored, the IE PRACH-Partitioning and the 
	-- IE rach-TransportFormatSet shall be absent and the corresponding IEs in the following 
	-- PRACH-SystemInformationList-LCR-r4 shall be used
	prach-SystemInformationList-LCR-r4	PRACH-SystemInformationList-LCR-r4	OPTIONAL, 
	tdd128SpecificInfo				SEQUENCE {
		pusch-SysInfoList-SFN			PUSCH-SysInfoList-SFN-LCR-r4	OPTIONAL,
		pdsch-SysInfoList-SFN			PDSCH-SysInfoList-SFN-LCR-r4	OPTIONAL,
		pCCPCH-LCR-Extensions			PrimaryCCPCH-Info-LCR-r4-ext	OPTIONAL,
		sCCPCH-LCR-ExtensionsList		SCCPCH-SystemInformationList-LCR-r4-ext	OPTIONAL
	}																OPTIONAL,
	frequencyBandIndicator			RadioFrequencyBandFDD			OPTIONAL
}

SysInfoType6-v590ext-IEs ::= SEQUENCE {
	hcr-r5-SpecificInfo				SEQUENCE {
		pusch-SysInfoList-SFN			PUSCH-SysInfoList-SFN-HCR-r5	OPTIONAL,
		pdsch-SysInfoList-SFN			PDSCH-SysInfoList-SFN-HCR-r5	OPTIONAL
	}																	OPTIONAL
}

SysInfoType6-v650ext-IEs ::= SEQUENCE {
	frequencyBandIndicator2			RadioFrequencyBandFDD2
}

SysInfoType6-v690ext-IEs ::= SEQUENCE {
	additionalPRACH-TF-and-TFCS-CCCH-List	AdditionalPRACH-TF-and-TFCS-CCCH-List	OPTIONAL
}

SysInfoType6-v7xyext-IEs ::=		SEQUENCE {
	pusch-SysInfoList-SFN-VHCR			PUSCH-SysInfoList-SFN-VHCR		OPTIONAL,
	pdsch-SysInfoList-SFN-r7			PDSCH-SysInfoList-r7			OPTIONAL,
	prach-SystemInformationList-r7		PRACH-SystemInformationList-r7	OPTIONAL,
	sCCPCH-SystemInformationList-r7		SCCPCH-SystemInformationList-r7	OPTIONAL
}

SysInfoType7 ::=					SEQUENCE {
	-- Physical channel IEs
		modeSpecificInfo				CHOICE {
			fdd								SEQUENCE {
				ul-Interference					UL-Interference
			},
			tdd								NULL
		},
		prach-Information-SIB5-List		DynamicPersistenceLevelList,
		prach-Information-SIB6-List		DynamicPersistenceLevelList			OPTIONAL,
		expirationTimeFactor			ExpirationTimeFactor				OPTIONAL,
	-- Extension mechanism for non- release99 information
		nonCriticalExtensions			SEQUENCE {}							OPTIONAL
}

-- This IE is not used in this version of the specification.
-- It was kept only for backwards compatibility reasons
SysInfoType8 ::=					SEQUENCE {
	-- User equipment IEs
		-- dummy1, dummy2, dummy3 are not used in this version of the specification and
		-- they should be ignored by the receiver.
		dummy1							CPCH-Parameters,
	-- Physical channel IEs
		dummy2							CPCH-SetInfoList,
		dummy3							CSICH-PowerOffset,
	-- Extension mechanism for non- release99 information
		nonCriticalExtensions			SEQUENCE {}							OPTIONAL
}

-- This IE is not used in this version of the specification.
-- It was kept only for backwards compatibility reasons
SysInfoType9 ::=					SEQUENCE {
	-- Physical channel IEs
		-- dummy is not used in this version of the specification and
		-- it should be ignored by the receiver.
		dummy							CPCH-PersistenceLevelsList,
	-- Extension mechanism for non- release99 information
		nonCriticalExtensions			SEQUENCE {}							OPTIONAL
}

-- This IE is not used in this version of the specification.
-- It was kept only for backwards compatibility reasons
SysInfoType10 ::=					SEQUENCE {
	-- User equipment IEs
		-- dummy is not used in this version of the specification, it should
		-- not be sent and if received it should be ignored.
		dummy							DRAC-SysInfoList,
	-- Extension mechanism for non- release99 information
		nonCriticalExtensions			SEQUENCE {}							OPTIONAL
}

SysInfoType11 ::=					SEQUENCE {
		sib12indicator					BOOLEAN,
	-- Measurement IEs
		fach-MeasurementOccasionInfo	FACH-MeasurementOccasionInfo		OPTIONAL,
		measurementControlSysInfo		MeasurementControlSysInfo,
	-- Extension mechanism for non- release99 information
		v4b0NonCriticalExtensions		SEQUENCE {
			sysInfoType11-v4b0ext			SysInfoType11-v4b0ext-IEs		OPTIONAL,
			v590NonCriticalExtension		SEQUENCE {
				sysInfoType11-v590ext			SysInfoType11-v590ext-IEs,
				v690NonCriticalExtensions			SEQUENCE {
					sysInfoType11-v690ext			SysInfoType11-v690ext-IEs,
					nonCriticalExtensions			SEQUENCE {}						OPTIONAL
				}							OPTIONAL
			}							OPTIONAL
		}							OPTIONAL
}

SysInfoType11-v4b0ext-IEs ::= SEQUENCE {
	fach-MeasurementOccasionInfo-LCR-Ext	FACH-MeasurementOccasionInfo-LCR-r4-ext	OPTIONAL,
	measurementControlSysInfo-LCR			MeasurementControlSysInfo-LCR-r4-ext
}

SysInfoType11-v590ext-IEs ::= SEQUENCE {
	--The order of the list corresponds to the order of cell in newIntraFrequencyCellInfoList
	newIntraFrequencyCellInfoList-v590ext	SEQUENCE (SIZE (1..maxCellMeas)) OF
												CellSelectReselectInfo-v590ext	OPTIONAL,
	--The order of the list corresponds to the order of cell in newInterFrequencyCellInfoList
	newInterFrequencyCellInfoList-v590ext	SEQUENCE (SIZE (1..maxCellMeas)) OF
												CellSelectReselectInfo-v590ext	OPTIONAL,
	--The order of the list corresponds to the order of cell in newInterRATCellInfoList
	newInterRATCellInfoList-v590ext			SEQUENCE (SIZE (1..maxCellMeas)) OF
												CellSelectReselectInfo-v590ext	OPTIONAL,
	intraFreqEventCriteriaList-v590ext		Intra-FreqEventCriteriaList-v590ext		OPTIONAL,
	intraFreqReportingCriteria-1b-r5		IntraFreqReportingCriteria-1b-r5	OPTIONAL,
	intraFreqEvent-1d-r5					IntraFreqEvent-1d-r5				OPTIONAL
}

SysInfoType11-v690ext-IEs ::= SEQUENCE {
	-- Measurement IEs
	interFreqRACHReportingInfo			InterFreqRACHReportingInfo			OPTIONAL
}

SysInfoType12 ::=					SEQUENCE {
	-- Measurement IEs
		fach-MeasurementOccasionInfo	FACH-MeasurementOccasionInfo		OPTIONAL,
		measurementControlSysInfo		MeasurementControlSysInfo,
	-- Extension mechanism for non- release99 information
		v4b0NonCriticalExtensions		SEQUENCE {
			sysInfoType12-v4b0ext			SysInfoType12-v4b0ext-IEs		OPTIONAL,
			v590NonCriticalExtension		SEQUENCE {
				sysInfoType12-v590ext			SysInfoType12-v590ext-IEs,
				v690NonCriticalExtensions			SEQUENCE {
					sysInfoType12-v690ext			SysInfoType12-v690ext-IEs,
					nonCriticalExtensions			SEQUENCE {}						OPTIONAL
				}							OPTIONAL
			}							OPTIONAL
		}							OPTIONAL
}

SysInfoType12-v4b0ext-IEs ::= SEQUENCE {
	fach-MeasurementOccasionInfo-LCR-Ext	FACH-MeasurementOccasionInfo-LCR-r4-ext	OPTIONAL,
	measurementControlSysInfo-LCR			MeasurementControlSysInfo-LCR-r4-ext
}

SysInfoType12-v590ext-IEs ::= SEQUENCE {
	--The order of the list corresponds to the order of cell in newIntraFrequencyCellInfoList
	newIntraFrequencyCellInfoList-v590ext	SEQUENCE (SIZE (1..maxCellMeas)) OF
												CellSelectReselectInfo-v590ext	OPTIONAL,
	--The order of the list corresponds to the order of cell in newInterFrequencyCellInfoList
	newInterFrequencyCellInfoList-v590ext	SEQUENCE (SIZE (1..maxCellMeas)) OF
												CellSelectReselectInfo-v590ext	OPTIONAL,
	--The order of the list corresponds to the order of cell in newInterRATCellInfoList
	newInterRATCellInfoList-v590ext			SEQUENCE (SIZE (1..maxCellMeas)) OF
												CellSelectReselectInfo-v590ext	OPTIONAL,
	intraFreqEventCriteriaList-v590ext		Intra-FreqEventCriteriaList-v590ext		OPTIONAL,
	intraFreqReportingCriteria-1b-r5		IntraFreqReportingCriteria-1b-r5	OPTIONAL,
	intraFreqEvent-1d-r5					IntraFreqEvent-1d-r5				OPTIONAL
}

SysInfoType12-v690ext-IEs ::= SEQUENCE {
	-- Measurement IEs
	interFreqRACHReportingInfo			InterFreqRACHReportingInfo			OPTIONAL
}

SysInfoType13 ::=					SEQUENCE {
	-- Core network IEs
		cn-DomainSysInfoList			CN-DomainSysInfoList,
	-- User equipment IEs
		ue-IdleTimersAndConstants		UE-IdleTimersAndConstants			OPTIONAL,
		capabilityUpdateRequirement		CapabilityUpdateRequirement			OPTIONAL,
	-- Extension mechanism for non- release99 information
		v3a0NonCriticalExtensions			SEQUENCE { 
			sysInfoType13-v3a0ext			SysInfoType13-v3a0ext-IEs,
			v4b0NonCriticalExtensions		SEQUENCE {
				sysInfoType13-v4b0ext			SysInfoType13-v4b0ext-IEs,
			-- Extension mechanism for non- release99 information
				v7xyNonCriticalExtensions		SEQUENCE {
					sysInfoType13-v7xyext			SysInfoType13-v7xyext-IEs,
					nonCriticalExtensions			SEQUENCE {}						OPTIONAL
				}							OPTIONAL
			}							OPTIONAL
		}							OPTIONAL
}

SysInfoType13-v3a0ext-IEs ::= SEQUENCE {
	ue-IdleTimersAndConstants-v3a0ext		UE-IdleTimersAndConstants-v3a0ext
}

SysInfoType13-v4b0ext-IEs ::= SEQUENCE {
	capabilityUpdateRequirement-r4Ext	CapabilityUpdateRequirement-r4-ext	OPTIONAL
}

SysInfoType13-v7xyext-IEs ::= SEQUENCE {
	capabilityUpdateRequirement-r7Ext	CapabilityUpdateRequirement-r7-ext	OPTIONAL
}

SysInfoType13-1 ::=					SEQUENCE {
	-- ANSI-41 IEs
		ansi-41-RAND-Information		ANSI-41-RAND-Information,
	-- Extension mechanism for non- release99 information
		nonCriticalExtensions			SEQUENCE {}							OPTIONAL
}

SysInfoType13-2 ::=					SEQUENCE {
	-- ANSI-41 IEs
		ansi-41-UserZoneID-Information	ANSI-41-UserZoneID-Information,
	-- Extension mechanism for non- release99 information
		nonCriticalExtensions			SEQUENCE {}							OPTIONAL
}

SysInfoType13-3 ::=					SEQUENCE {
	-- ANSI-41 IEs
		ansi-41-PrivateNeighbourListInfo ANSI-41-PrivateNeighbourListInfo,
	-- Extension mechanism for non- release99 information
		nonCriticalExtensions			SEQUENCE {}							OPTIONAL
}

SysInfoType13-4 ::=					SEQUENCE {
	-- ANSI-41 IEs
		ansi-41-GlobalServiceRedirectInfo
										ANSI-41-GlobalServiceRedirectInfo,
	-- Extension mechanism for non- release99 information
		nonCriticalExtensions			SEQUENCE {}							OPTIONAL
}

ANSI-41-GlobalServiceRedirectInfo ::= 	ANSI-41-NAS-Parameter
ANSI-41-PrivateNeighbourListInfo ::= 	ANSI-41-NAS-Parameter
ANSI-41-RAND-Information ::=			ANSI-41-NAS-Parameter
ANSI-41-UserZoneID-Information ::= 		ANSI-41-NAS-Parameter


SysInfoType14 ::=					SEQUENCE {
	-- Physical channel IEs
		individualTS-InterferenceList	IndividualTS-InterferenceList,
		expirationTimeFactor			ExpirationTimeFactor				OPTIONAL,
	-- Extension mechanism for non- release99 information
		nonCriticalExtensions			SEQUENCE {}							OPTIONAL
}

SysInfoType15 ::=					SEQUENCE {
	-- Measurement IEs
		
		ue-positioning-GPS-CipherParameters		UE-Positioning-CipherParameters		OPTIONAL,
		ue-positioning-GPS-ReferenceLocation	ReferenceLocation,
		ue-positioning-GPS-ReferenceTime		UE-Positioning-GPS-ReferenceTime,

		ue-positioning-GPS-Real-timeIntegrity		BadSatList							OPTIONAL,
	-- Extension mechanism for non- release99 information
		v4b0NonCriticalExtensions			SEQUENCE { 
			sysInfoType15-v4b0ext				SysInfoType15-v4b0ext-IEs,
		-- Extension mechanism for non- release4 information
			nonCriticalExtensions				SEQUENCE {}				OPTIONAL
		}	OPTIONAL
}

SysInfoType15-v4b0ext-IEs ::= SEQUENCE {
	up-Ipdl-Parameters-TDD			UE-Positioning-IPDL-Parameters-TDD-r4-ext	OPTIONAL
}

SysInfoType15-1 ::=					SEQUENCE {
	-- DGPS corrections
		ue-positioning-GPS-DGPS-Corrections			UE-Positioning-GPS-DGPS-Corrections,

	-- Extension mechanism for non- release99 information
		nonCriticalExtensions			SEQUENCE {}				OPTIONAL
} 

SysInfoType15-2 ::=					SEQUENCE {
	-- Ephemeris and clock corrections
		transmissionTOW					INTEGER (0..604799),
		satID							SatID,
		ephemerisParameter				EphemerisParameter,

	-- Extension mechanism for non- release99 information
		nonCriticalExtensions			SEQUENCE {}			OPTIONAL
} 

SysInfoType15-3 ::=					SEQUENCE {
	-- Almanac and other data
		transmissionTOW					INTEGER (0.. 604799),
		ue-positioning-GPS-Almanac					UE-Positioning-GPS-Almanac				OPTIONAL,
		ue-positioning-GPS-IonosphericModel			UE-Positioning-GPS-IonosphericModel		OPTIONAL,
		ue-positioning-GPS-UTC-Model				UE-Positioning-GPS-UTC-Model			OPTIONAL,
		satMask							BIT STRING (SIZE (1..32))	OPTIONAL,
		lsbTOW							BIT STRING (SIZE (8))		OPTIONAL,
	-- Extension mechanism for non- release99 information
		nonCriticalExtensions			SEQUENCE {}					OPTIONAL
} 

SysInfoType15-4 ::=					SEQUENCE {
	-- Measurement IEs
		ue-positioning-OTDOA-CipherParameters	UE-Positioning-CipherParameters			OPTIONAL,
		ue-positioning-OTDOA-AssistanceData		UE-Positioning-OTDOA-AssistanceData,
		v3a0NonCriticalExtensions			SEQUENCE {
			sysInfoType15-4-v3a0ext				SysInfoType15-4-v3a0ext,
		-- Extension mechanism for non- release99 information
			v4b0NonCriticalExtensions			SEQUENCE {
				sysInfoType15-4-v4b0ext				SysInfoType15-4-v4b0ext,
				nonCriticalExtensions				SEQUENCE {}		OPTIONAL
			}	OPTIONAL
		}	OPTIONAL
}

SysInfoType15-4-v3a0ext ::= SEQUENCE {
	sfn-Offset-Validity				SFN-Offset-Validity		OPTIONAL
}

SysInfoType15-4-v4b0ext ::= SEQUENCE {
	ue-Positioning-OTDOA-AssistanceData-r4ext	UE-Positioning-OTDOA-AssistanceData-r4ext	OPTIONAL
}

SysInfoType15-5 ::=					SEQUENCE {
	-- Measurement IEs
		ue-positioning-OTDOA-AssistanceData-UEB		UE-Positioning-OTDOA-AssistanceData-UEB,
		v3a0NonCriticalExtensions			SEQUENCE {
			sysInfoType15-5-v3a0ext				SysInfoType15-5-v3a0ext,
		-- Extension mechanism for non- release99 information
			nonCriticalExtensions				SEQUENCE {}		OPTIONAL
		}	OPTIONAL
}

SysInfoType15-5-v3a0ext ::= SEQUENCE {
	sfn-Offset-Validity			SFN-Offset-Validity		OPTIONAL
}

SysInfoType16 ::=					SEQUENCE {
	-- Radio bearer IEs
		preDefinedRadioConfiguration	PreDefRadioConfiguration,
	-- Extension mechanism for non- release99 information
		nonCriticalExtensions			SEQUENCE {}							OPTIONAL
}

SysInfoType17 ::=					SEQUENCE {
	-- Physical channel IEs
		-- If PDSCH/PUSCH is configured for 1.28Mcps TDD, pusch-SysInfoList and
		-- pdsch-SysInfoList should be absent and the info included in the
		-- tdd128SpecificInfo instead.
		-- If PDSCH/PUSCH is configured for 3.84Mcps TDD in R5, HCR-r5-SpecificInfo should also be 
		-- included.
		pusch-SysInfoList				PUSCH-SysInfoList				OPTIONAL,
		pdsch-SysInfoList				PDSCH-SysInfoList				OPTIONAL,
	-- Extension mechanism for non- release99 information
		v4b0NonCriticalExtensions		SEQUENCE {
			sysInfoType17-v4b0ext			SysInfoType17-v4b0ext-IEs,
			v590NonCriticalExtensions	SEQUENCE {
				sysInfoType17-v590ext			SysInfoType17-v590ext-IEs		OPTIONAL,
				v7xyNonCriticalExtensions		SEQUENCE {
					sysInfoType17-v7xyext			SysInfoType17-v7xyext-IEs,
					nonCriticalExtensions			SEQUENCE {}				OPTIONAL
				}							OPTIONAL
			}							OPTIONAL
		}							OPTIONAL
}

SysInfoType17-v4b0ext-IEs ::= SEQUENCE {
	tdd128SpecificInfo				SEQUENCE {
		pusch-SysInfoList				PUSCH-SysInfoList-LCR-r4		OPTIONAL,
		pdsch-SysInfoList				PDSCH-SysInfoList-LCR-r4		OPTIONAL
	}																	OPTIONAL
}

SysInfoType17-v590ext-IEs ::= SEQUENCE {
	hcr-r5-SpecificInfo				SEQUENCE {
		pusch-SysInfoList			PUSCH-SysInfoList-HCR-r5	OPTIONAL,
		pdsch-SysInfoList			PDSCH-SysInfoList-HCR-r5	OPTIONAL
	}															OPTIONAL
}

SysInfoType17-v7xyext-IEs ::=		SEQUENCE {
	pusch-SysInfoList-SFN-VHCR			PUSCH-SysInfoList-SFN-VHCR		OPTIONAL,
	pdsch-SysInfoList-r7				PDSCH-SysInfoList-r7			OPTIONAL
}

SysInfoType18 ::=						SEQUENCE {
		idleModePLMNIdentities			PLMNIdentitiesOfNeighbourCells		OPTIONAL,
		connectedModePLMNIdentities	PLMNIdentitiesOfNeighbourCells		OPTIONAL,
	-- Extension mechanism for non- release99 information
		nonCriticalExtensions			SEQUENCE {}		OPTIONAL
}

SysInfoTypeSB1 ::=					SEQUENCE {
	-- Other IEs
		sib-ReferenceList				SIB-ReferenceList,
	-- Extension mechanism for non- release99 information
		nonCriticalExtensions			SEQUENCE {}							OPTIONAL
}

SysInfoTypeSB2 ::=					SEQUENCE {
	-- Other IEs
		sib-ReferenceList				SIB-ReferenceList,
	-- Extension mechanism for non- release99 information
		nonCriticalExtensions			SEQUENCE {}							OPTIONAL
}

TDD-UMTS-Frequency-List ::= 			SEQUENCE (SIZE (1..maxNumTDDFreqs)) OF
											FrequencyInfoTDD


SegCount ::=						INTEGER (1..16)

SegmentIndex ::=					INTEGER (1..15)

SIB-Data-fixed ::=					BIT STRING (SIZE (222))

SIB-Data-variable ::=				BIT STRING (SIZE (1..214))

PLMN-ValueTag ::=					INTEGER (1..256)

MIB-ValueTag ::=					INTEGER (1..8)

NCC ::=								INTEGER (0..7)

CellValueTag ::=						INTEGER (1..4)

PredefinedConfigIdentityAndValueTag ::=	SEQUENCE {
	predefinedConfigIdentity				PredefinedConfigIdentity,
	predefinedConfigValueTag				PredefinedConfigValueTag
}

SIBOccurIdentity ::=			INTEGER (0..15)

SIBOccurrenceIdentityAndValueTag ::=	SEQUENCE {
	sibOccurIdentity				SIBOccurIdentity,
	sibOccurValueTag				SIBOccurValueTag
}

SIBOccurValueTag ::=			INTEGER (0..15)

NAS-SystemInformationGSM-MAP ::= 	OCTET STRING (SIZE (1..8))

CN-DomainSysInfoList ::=			SEQUENCE (SIZE (1..maxCNdomains)) OF
										CN-DomainSysInfo

UE-ConnTimersAndConstants ::=		SEQUENCE {
-- Optional is used also for parameters for which the default value is the last one read in SIB1
-- t-301 and n-301 should not be used by the UE in this version of the specification
	t-301								T-301								DEFAULT ms2000,
	n-301								N-301								DEFAULT 2,
	t-302								T-302								DEFAULT ms4000,
	n-302								N-302								DEFAULT 3,
	t-304								T-304								DEFAULT ms2000,
	n-304								N-304								DEFAULT 2,
	t-305								T-305								DEFAULT m30,
	t-307								T-307								DEFAULT s30,
	t-308								T-308								DEFAULT ms160,
	t-309								T-309								DEFAULT 5,
	t-310								T-310								DEFAULT ms160,
	n-310								N-310								DEFAULT 4,
	t-311								T-311								DEFAULT ms2000,
	t-312								T-312								DEFAULT 1,
	-- n-312 shall be ignored if n-312 in UE-ConnTimersAndConstants-v3a0ext is present, and the
	-- value of that element shall be used instead.
	n-312								N-312								DEFAULT s1,
	t-313								T-313								DEFAULT 3,
	n-313								N-313								DEFAULT s20,
	t-314								T-314								DEFAULT s12,
	t-315								T-315								DEFAULT s180,
	-- n-315 shall be ignored if n-315 in UE-ConnTimersAndConstants-v3a0ext is present, and the
	-- value of that element shall be used instead.
	n-315								N-315								DEFAULT s1,
	t-316								T-316								DEFAULT s30,
	t-317								T-317								DEFAULT infinity4
}

UE-IdleTimersAndConstants ::=		SEQUENCE {
	t-300								T-300,
	n-300								N-300,
	t-312								T-312,
	-- n-312 shall be ignored if n-312 in UE-IdleTimersAndConstants-v3a0ext is present, and the
	-- value of that element shall be used instead.
	n-312								N-312	
}

UE-ConnTimersAndConstants-v3a0ext ::=		SEQUENCE {
	n-312								N-312ext								OPTIONAL,
	n-315								N-315ext								OPTIONAL
}

URA-IdentityList ::=				SEQUENCE (SIZE (1..maxURA)) OF
										URA-Identity

CellIdentity ::=					BIT STRING (SIZE (28))

CellIdentity-PerRL-List ::=			SEQUENCE (SIZE (1..maxRL)) OF CellIdentity

CellSelectReselectInfoSIB-3-4 ::=	SEQUENCE {
	mappingInfo							MappingInfo							OPTIONAL,
	cellSelectQualityMeasure			CHOICE {
		cpich-Ec-N0							SEQUENCE {
			-- Default value for q-HYST-2-S is q-HYST-1-S
			q-HYST-2-S							Q-Hyst-S					OPTIONAL
			-- Default value for q-HYST-2-S is q-HYST-1-S
		},
		cpich-RSCP							NULL
	},
	modeSpecificInfo					CHOICE {
		fdd									SEQUENCE {
			s-Intrasearch						S-SearchQual				OPTIONAL,
			s-Intersearch						S-SearchQual				OPTIONAL,
			s-SearchHCS							S-SearchRXLEV				OPTIONAL,
			rat-List							RAT-FDD-InfoList			OPTIONAL,
			q-QualMin							Q-QualMin,
			q-RxlevMin							Q-RxlevMin
		},
		tdd									SEQUENCE {
			s-Intrasearch						S-SearchRXLEV				OPTIONAL,
			s-Intersearch						S-SearchRXLEV				OPTIONAL,
			s-SearchHCS							S-SearchRXLEV				OPTIONAL,
			rat-List							RAT-TDD-InfoList			OPTIONAL,
			q-RxlevMin							Q-RxlevMin
		}
	},	
	q-Hyst-l-S							Q-Hyst-S,
	t-Reselection-S						T-Reselection-S,
	hcs-ServingCellInformation			HCS-ServingCellInformation			OPTIONAL,
	maxAllowedUL-TX-Power				MaxAllowedUL-TX-Power
}

CellAccessRestriction ::=			SEQUENCE {
	cellBarred							CellBarred,
	cellReservedForOperatorUse			ReservedIndicator,
	cellReservationExtension			ReservedIndicator,
	-- NOTE: IE accessClassBarredList should not be included if the IE CellAccessRestriction
	-- is included in the IE SysInfoType4
	accessClassBarredList				AccessClassBarredList				OPTIONAL
}

Mapping-LCR-r4 ::=					SEQUENCE {
	mappingFunctionParameterList		MappingFunctionParameterList
}

MappingFunctionParameter ::=		SEQUENCE {
	functionType						MappingFunctionType,
	mapParameter1						MapParameter						OPTIONAL,
	mapParameter2						MapParameter,
	-- The presence of upperLimit is conditional on the number of repetition
	upperLimit							UpperLimit							OPTIONAL
}

MappingFunctionParameterList ::= 	SEQUENCE (SIZE (1..maxMeasIntervals)) OF
										MappingFunctionParameter

CellSelectReselectInfo-v590ext ::= SEQUENCE {
	deltaQrxlevmin					DeltaQrxlevmin					OPTIONAL,
	deltaQhcs						DeltaRSCP						OPTIONAL
}

CellSelectReselectInfoTreselectionScaling-v5c0ext ::= SEQUENCE {
	-- For speed detection, the same HCS parameters are utilised
	non-HCS-t-CR-Max							T-CRMax									OPTIONAL,
	speedDependentScalingFactor					SpeedDependentScalingFactor				OPTIONAL,
	interFrequencyTreselectionScalingFactor		TreselectionScalingFactor				OPTIONAL,
	interRATTreselectionScalingFactor			TreselectionScalingFactor				OPTIONAL
}

DomainSpecificAccessRestrictionParam-v670ext ::= SEQUENCE {		
		cSDomainSpecificAccessRestriction		DomainSpecificAccessRestriction-v670ext,
		pSDomainSpecificAccessRestriction		DomainSpecificAccessRestriction-v670ext
}

DomainSpecificAccessRestrictionForSharedNetwork-v670ext ::= CHOICE {
		domainSpecificAccessRestictionList					DomainSpecificAccessRestrictionList-v670ext,
		domainSpecificAccessRestictionParametersForAll		DomainSpecificAccessRestrictionParam-v670ext
}

UE-IdleTimersAndConstants-v3a0ext ::=		SEQUENCE {
	n-312								N-312ext								OPTIONAL
}

CellSelectReselectInfoPCHFACH-v5b0ext ::= SEQUENCE {
	q-Hyst-l-S-PCH				Q-Hyst-S-Fine						OPTIONAL,
	q-Hyst-l-S-FACH				Q-Hyst-S-Fine						OPTIONAL,
	q-Hyst-2-S-PCH				Q-Hyst-S-Fine						OPTIONAL,
	q-Hyst-2-S-FACH				Q-Hyst-S-Fine						OPTIONAL,
	t-Reselection-S-PCH			T-Reselection-S						OPTIONAL,
	t-Reselection-S-FACH		T-Reselection-S-Fine				OPTIONAL
}

PICH-PowerOffset ::=				INTEGER (-10..5)

AICH-PowerOffset ::=				INTEGER (-22..5)

PUSCH-SysInfoList-SFN ::=			SEQUENCE (SIZE (1..maxPUSCH)) OF
										SEQUENCE {
	pusch-SysInfo							PUSCH-SysInfo,
	sfn-TimeInfo							SFN-TimeInfo					OPTIONAL
}

OpenLoopPowerControl-TDD ::=		SEQUENCE {
	primaryCCPCH-TX-Power				PrimaryCCPCH-TX-Power,
	-- alpha, prach-ConstantValue, dpch-ConstantValue and pusch-ConstantValue
	-- shall be ignored in 1.28Mcps TDD mode.
	alpha								Alpha						OPTIONAL,
	prach-ConstantValue					ConstantValueTdd,
	dpch-ConstantValue					ConstantValueTdd,
	pusch-ConstantValue					ConstantValueTdd			OPTIONAL
}

PrimaryCCPCH-Info ::=				CHOICE {
	fdd									SEQUENCE {
		tx-DiversityIndicator				BOOLEAN
	},
	tdd									SEQUENCE {
		-- syncCase should be ignored for 1.28Mcps TDD mode
		syncCase 							CHOICE {
			syncCase1							SEQUENCE {
				timeslot							TimeslotNumber					
			},
			syncCase2							SEQUENCE {
				timeslotSync2						TimeslotSync2
			}
		}																	OPTIONAL,
		cellParametersID					CellParametersID				OPTIONAL,
		sctd-Indicator						BOOLEAN
	}
}

PRACH-SystemInformationList ::=		SEQUENCE (SIZE (1..maxPRACH)) OF
										PRACH-SystemInformation

PRACH-SystemInformationList-r7 ::=	SEQUENCE (SIZE (1..maxPRACH)) OF
										PRACH-SystemInformation-r7

PRACH-SystemInformationList-LCR-r4 ::=	SEQUENCE (SIZE (1..maxPRACH)) OF
											PRACH-SystemInformation-LCR-r4

SCCPCH-SystemInformationList ::=	SEQUENCE (SIZE (1..maxSCCPCH)) OF
										SCCPCH-SystemInformation                                            

CBS-DRX-Level1Information ::=		SEQUENCE {
	ctch-AllocationPeriod				INTEGER (1..256),
	cbs-FrameOffset						INTEGER (0..255)
}

PNBSCH-Allocation-r4 ::=				SEQUENCE {
		numberOfRepetitionsPerSFNPeriod	ENUMERATED {
											c2, c3, c4, c5, c6, c7, c8, c9, c10,
											c12, c14, c16, c18, c20, c24, c28, c32,
											c36, c40, c48, c56, c64, c72, c80  }
}

OpenLoopPowerControl-IPDL-TDD-r4 ::=	SEQUENCE {
	ipdl-alpha							Alpha,
	maxPowerIncrease					MaxPowerIncrease-r4
}

PrimaryCCPCH-Info-LCR-r4-ext ::=	SEQUENCE {
	tstd-Indicator						BOOLEAN
}

SCCPCH-SystemInformationList-LCR-r4-ext ::=	SEQUENCE (SIZE (1..maxSCCPCH)) OF
												SCCPCH-SystemInformation-LCR-r4-ext


RadioFrequencyBandFDD ::=			ENUMERATED {
	-- fdd2100, fdd1900, fdd1800 correspond to Band I, Band II and Band III respectively
										fdd2100,
										fdd1900,
										fdd1800, 
										bandVI, 
										bandIV,
										bandV,
										bandVII,
										extension-indicator }

PUSCH-SysInfoList-SFN-HCR-r5 ::=			SEQUENCE (SIZE (1..maxPUSCH)) OF
										SEQUENCE {
	pusch-SysInfo							PUSCH-SysInfo-HCR-r5,
	sfn-TimeInfo							SFN-TimeInfo					OPTIONAL
}

RadioFrequencyBandFDD2 ::=			ENUMERATED {
										bandVIII,
										bandIX,
										bandX,
										bandXI,
										bandXII,
										bandXIII,
										bandXIV,
										bandXV,
										bandXVI,
										bandXVII, 
										bandXVIII,
										bandXIX,
										bandXX,
										bandXXI,
										bandXXII,
										extension-indicator }

MBMS-MCCH-ConfigurationInfo-r6 ::=	SEQUENCE {
	accessInfoPeriodCoefficient			INTEGER (0..3),
	repetitionPeriodCoefficient			INTEGER (0..3),
	modificationPeriodCoefficient		INTEGER (7..10),
	rlc-Info							RLC-Info-MCCH-r6,
	tctf-Presence						MBMS-TCTF-Presence					OPTIONAL
}

SCCPCH-SystemInformation-MBMS-r6 ::= SEQUENCE {
	secondaryCCPCHInfo-MBMS				SecondaryCCPCHInfo-MBMS-r6,
	transportFormatCombinationSet		TFCS,
	fachCarryingMCCH					SEQUENCE {
		mcch-transportFormatSet				TransportFormatSet,
		mcch-ConfigurationInfo				MBMS-MCCH-ConfigurationInfo-r6
	},
	fachCarryingMTCH-List				MBMS-FACHCarryingMTCH-List			OPTIONAL,
	-- If schedulingInformation is provided
	fachCarryingMSCH					SEQUENCE {
		msch-transportFormatSet				TransportFormatSet,
		msch-ConfigurationInfo				MBMS-MSCH-ConfigurationInfo-r6
	}		OPTIONAL
}

AdditionalPRACH-TF-and-TFCS-CCCH-List ::=	SEQUENCE (SIZE (1..maxPRACH)) OF
										AdditionalPRACH-TF-and-TFCS-CCCH


CBS-DRX-Level1Information-extension-r6 ::=	ENUMERATED {p8, p16, p32, p64, p128, p256}

PUSCH-SysInfoList-SFN-VHCR ::=		SEQUENCE (SIZE (1..maxPUSCH)) OF
										SEQUENCE {
	pusch-SysInfo-VHCR						PUSCH-SysInfo-VHCR,
	sfn-TimeInfo							SFN-TimeInfo					OPTIONAL
}

PDSCH-SysInfoList-SFN ::=			SEQUENCE (SIZE (1..maxPDSCH)) OF
										SEQUENCE {
	pdsch-SysInfo							PDSCH-SysInfo,
	sfn-TimeInfo							SFN-TimeInfo					OPTIONAL
}

PDSCH-SysInfoList-SFN-HCR-r5 ::=			SEQUENCE (SIZE (1..maxPDSCH)) OF
										SEQUENCE {
	pdsch-SysInfo							PDSCH-SysInfo-HCR-r5,
	sfn-TimeInfo							SFN-TimeInfo					OPTIONAL
}

PDSCH-SysInfoList-SFN-LCR-r4 ::=	SEQUENCE (SIZE (1..maxPDSCH)) OF
										SEQUENCE {
	pdsch-SysInfo							PDSCH-SysInfo-LCR-r4,
	sfn-TimeInfo							SFN-TimeInfo					OPTIONAL
}

PDSCH-SysInfoList-r7 ::=			SEQUENCE (SIZE (1..maxPDSCH)) OF PDSCH-SysInfo-r7

SCCPCH-SystemInformation-MBMS-r7 ::= SEQUENCE {
	secondaryCCPCHInfo-MBMS				SecondaryCCPCHInfo-MBMS-r7,
	transportFormatCombinationSet		TFCS,
	fachCarryingMCCH					SEQUENCE {
		mcch-transportFormatSet				TransportFormatSet,
		mcch-ConfigurationInfo				MBMS-MCCH-ConfigurationInfo-r6
	},
	fachCarryingMTCH-List				MBMS-FACHCarryingMTCH-List			OPTIONAL,
	-- If schedulingInformation is provided
	fachCarryingMSCH					SEQUENCE {
		msch-transportFormatSet				TransportFormatSet,
		msch-ConfigurationInfo				MBMS-MSCH-ConfigurationInfo-r6
	}		OPTIONAL
}

SCCPCH-SystemInformationList-r7 ::=	SEQUENCE (SIZE (1..maxSCCPCH)) OF
										SCCPCH-SystemInformation-r7

CSICH-PowerOffset ::=				INTEGER (-10..5)

UL-Interference ::=					INTEGER (-110..-70)

DynamicPersistenceLevelList ::=		SEQUENCE (SIZE (1..maxPRACH)) OF
										DynamicPersistenceLevel

ExpirationTimeFactor ::=				INTEGER (1..8)

CPCH-Parameters ::=					SEQUENCE {
	initialPriorityDelayList			InitialPriorityDelayList			OPTIONAL,
	backoffControlParams				BackoffControlParams,
	-- TABULAR: TPC step size nested inside PowerControlAlgorithm
	powerControlAlgorithm				PowerControlAlgorithm,
	dl-DPCCH-BER						DL-DPCCH-BER
}

CPCH-SetInfoList ::=				SEQUENCE (SIZE (1..maxCPCHsets)) OF
										CPCH-SetInfo

CPCH-PersistenceLevelsList ::=		SEQUENCE (SIZE (1..maxCPCHsets)) OF
										CPCH-PersistenceLevels
 
DRAC-SysInfoList ::=				SEQUENCE (SIZE (1..maxDRACclasses)) OF
										DRAC-SysInfo

FACH-MeasurementOccasionInfo ::=	SEQUENCE {
	fACH-meas-occasion-coeff			INTEGER (1..12)						OPTIONAL,
	inter-freq-FDD-meas-ind				BOOLEAN,
	-- inter-freq-TDD-meas-ind is for 3.84Mcps TDD and 7.68 Mcps TDD. For 1.28Mcps TDD, the IE in
	-- FACH-MeasurementOccasionInfo-LCR-r4-ext is used.
	inter-freq-TDD-meas-ind				BOOLEAN,
	inter-RAT-meas-ind					SEQUENCE (SIZE (1..maxOtherRAT)) OF
											RAT-Type						OPTIONAL
}

MeasurementControlSysInfo ::=		SEQUENCE {
	-- CHOICE cellSelectQualityMeasure represents PCCPCH-RSCP in TDD mode.
	use-of-HCS							CHOICE	{
		hcs-not-used 					SEQUENCE	{
			cellSelectQualityMeasure	CHOICE	{
				cpich-RSCP				SEQUENCE	{
					intraFreqMeasurementSysInfo			IntraFreqMeasurementSysInfo-RSCP	OPTIONAL,
					interFreqMeasurementSysInfo			InterFreqMeasurementSysInfo-RSCP	OPTIONAL
				},
				cpich-Ec-N0				SEQUENCE	{
					intraFreqMeasurementSysInfo			IntraFreqMeasurementSysInfo-ECN0		OPTIONAL,
					interFreqMeasurementSysInfo			InterFreqMeasurementSysInfo-ECN0	OPTIONAL
				}
			},
			interRATMeasurementSysInfo		InterRATMeasurementSysInfo-B		OPTIONAL
		},
		hcs-used						SEQUENCE	{
			cellSelectQualityMeasure	CHOICE	{
				cpich-RSCP				SEQUENCE	{
					intraFreqMeasurementSysInfo			IntraFreqMeasurementSysInfo-HCS-RSCP			OPTIONAL,
					interFreqMeasurementSysInfo			InterFreqMeasurementSysInfo-HCS-RSCP			OPTIONAL
				},
				cpich-Ec-N0				SEQUENCE	{
					intraFreqMeasurementSysInfo			IntraFreqMeasurementSysInfo-HCS-ECN0			OPTIONAL,
					interFreqMeasurementSysInfo			InterFreqMeasurementSysInfo-HCS-ECN0			OPTIONAL				}
			},
			interRATMeasurementSysInfo		InterRATMeasurementSysInfo		OPTIONAL
		}
	},

	trafficVolumeMeasSysInfo			TrafficVolumeMeasSysInfo			OPTIONAL,
	-- dummy is not used in this version of specification and it shall be ignored by the UE.
	dummy		UE-InternalMeasurementSysInfo		OPTIONAL
}

FACH-MeasurementOccasionInfo-LCR-r4-ext ::=	SEQUENCE {
	inter-freq-TDD128-meas-ind					BOOLEAN
}

MeasurementControlSysInfo-LCR-r4-ext ::=	SEQUENCE {
	-- CHOICE use-of-HCS shall have the same value as the use-of-HCS
	-- in MeasurementControlSysInfo
	-- CHOICE cellSelectQualityMeasure represents PCCPCH-RSCP in TDD mode.
	use-of-HCS							CHOICE	{
		hcs-not-used 					SEQUENCE	{
			-- CHOICE cellSelectQualityMeasure shall have the same value as the
			-- cellSelectQualityMeasure in MeasurementControlSysInfo
			cellSelectQualityMeasure	CHOICE	{
				cpich-RSCP				SEQUENCE	{
					intraFreqMeasurementSysInfo	IntraFreqMeasurementSysInfo-RSCP-LCR-r4	OPTIONAL,
					interFreqMeasurementSysInfo	InterFreqMeasurementSysInfo-RSCP-LCR-r4	OPTIONAL
				},
				cpich-Ec-N0				SEQUENCE	{
					intraFreqMeasurementSysInfo	IntraFreqMeasurementSysInfo-ECN0-LCR-r4	OPTIONAL,
					interFreqMeasurementSysInfo	InterFreqMeasurementSysInfo-ECN0-LCR-r4	OPTIONAL
				}
			}
		},
		hcs-used						SEQUENCE	{
			-- CHOICE cellSelectQualityMeasure shall have the same value as the
			-- cellSelectQualityMeasure in MeasurementControlSysInfo
			cellSelectQualityMeasure	CHOICE	{
				cpich-RSCP				SEQUENCE	{
					intraFreqMeasurementSysInfo	IntraFreqMeasurementSysInfo-HCS-RSCP-LCR-r4	OPTIONAL,
					interFreqMeasurementSysInfo	InterFreqMeasurementSysInfo-HCS-RSCP-LCR-r4	OPTIONAL
				},
				cpich-Ec-N0				SEQUENCE	{
					intraFreqMeasurementSysInfo	IntraFreqMeasurementSysInfo-HCS-ECN0-LCR-r4	OPTIONAL,
					interFreqMeasurementSysInfo	InterFreqMeasurementSysInfo-HCS-ECN0-LCR-r4	OPTIONAL
				}
			}
		}
	}
}

Intra-FreqEventCriteriaList-v590ext ::= SEQUENCE (SIZE (1..maxMeasEvent)) OF
											DeltaRSCP

IntraFreqReportingCriteria-1b-r5 ::= SEQUENCE {
	periodicReportingInfo-1b			PeriodicReportingInfo-1b
}

IntraFreqEvent-1d-r5 ::=		SEQUENCE {
	triggeringCondition					TriggeringCondition2	OPTIONAL,
	useCIO								BOOLEAN					OPTIONAL
}

InterFreqRACHReportingInfo ::= SEQUENCE {
	modeSpecificInfo					CHOICE {
		fdd									SEQUENCE {
			interFreqRepQuantityRACH-FDD		InterFreqRepQuantityRACH-FDD
		},
		tdd									SEQUENCE {
			interFreqRepQuantityRACH-TDDList	InterFreqRepQuantityRACH-TDDList
		},
	interFreqRACHReportingThreshold		Threshold,
	maxReportedCellsOnRACHinterFreq		MaxReportedCellsOnRACHinterFreq
	}
}

PUSCH-SysInfoList-SFN-LCR-r4 ::=		SEQUENCE (SIZE (1..maxPUSCH)) OF
										SEQUENCE {
	pusch-SysInfo							PUSCH-SysInfo-LCR-r4,
	sfn-TimeInfo							SFN-TimeInfo					OPTIONAL
}

CapabilityUpdateRequirement ::=		SEQUENCE {
	ue-RadioCapabilityFDDUpdateRequirement	BOOLEAN,
	-- ue-RadioCapabilityTDDUpdateRequirement is for 3.84Mcps TDD update requirement
	ue-RadioCapabilityTDDUpdateRequirement	BOOLEAN,
	systemSpecificCapUpdateReqList		SystemSpecificCapUpdateReqList		OPTIONAL
}

CapabilityUpdateRequirement-r4-ext ::= SEQUENCE {
	ue-RadioCapabilityUpdateRequirement-TDD128	BOOLEAN
}

CapabilityUpdateRequirement-r4 ::=	SEQUENCE {
	ue-RadioCapabilityFDDUpdateRequirement-FDD	BOOLEAN,
	ue-RadioCapabilityTDDUpdateRequirement-TDD384	BOOLEAN,
	ue-RadioCapabilityTDDUpdateRequirement-TDD128	BOOLEAN,
	systemSpecificCapUpdateReqList		SystemSpecificCapUpdateReqList		OPTIONAL
}

CapabilityUpdateRequirement-r7-ext ::= SEQUENCE {
	ue-RadioCapabilityUpdateRequirement-TDD768	BOOLEAN
}

ANSI-41-NAS-Parameter ::=				BIT STRING (SIZE (1..2048))

IndividualTS-InterferenceList ::=	SEQUENCE (SIZE (1..maxTS)) OF
										IndividualTS-Interference

PUSCH-SysInfoList-LCR-r4 ::=		SEQUENCE (SIZE (1..maxPUSCH)) OF
										PUSCH-SysInfo-LCR-r4

UE-Positioning-CipherParameters ::=			SEQUENCE {
	cipheringKeyFlag					BIT STRING (SIZE (1)),
	cipheringSerialNumber				INTEGER (0..65535)
}

ReferenceLocation ::=			SEQUENCE {
	ellipsoidPointAltitudeEllipsoide		EllipsoidPointAltitudeEllipsoide
}

UE-Positioning-GPS-ReferenceTime ::=			SEQUENCE {
	gps-Week							INTEGER (0..1023),
	gps-tow-1msec						GPS-TOW-1msec,	utran-GPSReferenceTime				UTRAN-GPSReferenceTime				OPTIONAL,
	sfn-tow-Uncertainty					SFN-TOW-Uncertainty					OPTIONAL,
	utran-GPS-DriftRate					UTRAN-GPS-DriftRate					OPTIONAL,
	gps-TOW-AssistList					GPS-TOW-AssistList					OPTIONAL
}

BadSatList ::=						SEQUENCE (SIZE (1..maxSat)) OF
										INTEGER (0..63)

UE-Positioning-IPDL-Parameters-TDD-r4-ext ::=	SEQUENCE {
	ip-Spacing							IP-Spacing-TDD,
	ip-slot								INTEGER (0..14),
	ip-Start							INTEGER (0..4095),
	ip-PCCPCG							IP-PCCPCH-r4					OPTIONAL,
	burstModeParameters					BurstModeParameters
}

UE-Positioning-GPS-DGPS-Corrections ::=		SEQUENCE {
	gps-TOW								INTEGER (0..604799),
	statusHealth						DiffCorrectionStatus,
	dgps-CorrectionSatInfoList			DGPS-CorrectionSatInfoList
}

SatID ::=							INTEGER (0..63)

EphemerisParameter ::=						SEQUENCE {
	codeOnL2							BIT STRING (SIZE (2)),
	uraIndex							BIT STRING (SIZE (4)),
	satHealth							BIT STRING (SIZE (6)),
	iodc								BIT STRING (SIZE (10)),
	l2Pflag								BIT STRING (SIZE (1)),
	sf1Revd								SubFrame1Reserved,
	t-GD								BIT STRING (SIZE (8)),
	t-oc								BIT STRING (SIZE (16)),
	af2									BIT STRING (SIZE (8)),
	af1									BIT STRING (SIZE (16)),
	af0									BIT STRING (SIZE (22)),
	c-rs								BIT STRING (SIZE (16)),
	delta-n								BIT STRING (SIZE (16)),
	m0									BIT STRING (SIZE (32)),
	c-uc								BIT STRING (SIZE (16)),
	e									BIT STRING (SIZE (32)),
	c-us								BIT STRING (SIZE (16)),
	a-Sqrt								BIT STRING (SIZE (32)),
	t-oe								BIT STRING (SIZE (16)),
	fitInterval							BIT STRING (SIZE (1)),
	aodo								BIT STRING (SIZE (5)),
	c-ic								BIT STRING (SIZE (16)),
	omega0								BIT STRING (SIZE (32)),
	c-is								BIT STRING (SIZE (16)),
	i0									BIT STRING (SIZE (32)),
	c-rc								BIT STRING (SIZE (16)),
	omega								BIT STRING (SIZE (32)),
	omegaDot							BIT STRING (SIZE (24)),
	iDot								BIT STRING (SIZE (14))
}

UE-Positioning-GPS-Almanac ::=					SEQUENCE {
	wn-a								BIT STRING (SIZE (8)),
	almanacSatInfoList					AlmanacSatInfoList,
	sv-GlobalHealth						BIT STRING (SIZE (364))				OPTIONAL
}

UE-Positioning-GPS-IonosphericModel ::=		SEQUENCE {
	alfa0								BIT STRING (SIZE (8)),
	alfa1								BIT STRING (SIZE (8)),
	alfa2								BIT STRING (SIZE (8)),
	alfa3								BIT STRING (SIZE (8)),
	beta0								BIT STRING (SIZE (8)),
	beta1								BIT STRING (SIZE (8)),
	beta2								BIT STRING (SIZE (8)),
	beta3								BIT STRING (SIZE (8))
}

UE-Positioning-GPS-UTC-Model ::=				SEQUENCE {
	a1									BIT STRING (SIZE (24)),
	a0									BIT STRING (SIZE (32)),
	t-ot								BIT STRING (SIZE (8)),
	wn-t								BIT STRING (SIZE (8)),
	delta-t-LS							BIT STRING (SIZE (8)),
	wn-lsf								BIT STRING (SIZE (8)),
	dn									BIT STRING (SIZE (8)),
	delta-t-LSF							BIT STRING (SIZE (8))
}

UE-Positioning-OTDOA-AssistanceData ::=		SEQUENCE {
	ue-positioning-OTDOA-ReferenceCellInfo			UE-Positioning-OTDOA-ReferenceCellInfo				OPTIONAL,
	ue-positioning-OTDOA-NeighbourCellList				UE-Positioning-OTDOA-NeighbourCellList				OPTIONAL
}

SFN-Offset-Validity ::=			ENUMERATED { false }

UE-Positioning-OTDOA-AssistanceData-r4ext ::= SEQUENCE {
	-- In case of TDD these IPDL parameters shall be used for the reference cell instead of
	-- IPDL Parameters in IE UE-Positioning-OTDOA-ReferenceCellInfo
	ue-Positioning-IPDL-Parameters-TDD-r4-ext		UE-Positioning-IPDL-Parameters-TDD-r4-ext	OPTIONAL,
	-- These IPDL parameters shall be used for the neighbour cells in case of TDD instead of
	-- IPDL Parameters in IE UE-Positioning-OTDOA-NeighbourCellInfoList. The cells shall be 
	-- listed in the same order as in IE UE-Positioning-OTDOA-NeighbourCellInfoList
	ue-Positioning-IPDL-Parameters-TDDList-r4-ext	UE-Positioning-IPDL-Parameters-TDDList-r4-ext		OPTIONAL
}

UE-Positioning-OTDOA-AssistanceData-UEB ::=		SEQUENCE {
	ue-positioning-OTDOA-ReferenceCellInfo-UEB			UE-Positioning-OTDOA-ReferenceCellInfo-UEB				OPTIONAL,
	ue-positioning-OTDOA-NeighbourCellList-UEB				UE-Positioning-OTDOA-NeighbourCellList-UEB				OPTIONAL
}

PreDefRadioConfiguration ::=		SEQUENCE {
	-- Radio bearer IEs
		predefinedRB-Configuration			PredefinedRB-Configuration,
	-- Transport channel IEs
		preDefTransChConfiguration			PreDefTransChConfiguration,
	-- Physical channel IEs
		preDefPhyChConfiguration			PreDefPhyChConfiguration
}

PUSCH-SysInfoList ::=				SEQUENCE (SIZE (1..maxPUSCH)) OF
										PUSCH-SysInfo

PDSCH-SysInfoList-LCR-r4 ::=		SEQUENCE (SIZE (1..maxPDSCH)) OF
										PDSCH-SysInfo-LCR-r4

                                  
PUSCH-SysInfoList-HCR-r5 ::=			SEQUENCE (SIZE (1..maxPUSCH)) OF PUSCH-SysInfo-HCR-r5

      PLMNIdentitiesOfNeighbourCells ::=	SEQUENCE {
		plmnsOfIntraFreqCellsList		PLMNsOfIntraFreqCellsList			OPTIONAL,
		plmnsOfInterFreqCellsList		PLMNsOfInterFreqCellsList			OPTIONAL,
		plmnsOfInterRATCellsList		PLMNsOfInterRATCellsList			OPTIONAL
}

SIB-ReferenceList ::=				SEQUENCE (SIZE (1..maxSIB)) OF
										SchedulingInformationSIB

FrequencyInfoTDD ::=				SEQUENCE {
	uarfcn-Nt							UARFCN
}

PredefinedConfigValueTag ::=		INTEGER (0..15)

CN-DomainSysInfo ::=				SEQUENCE {
	cn-DomainIdentity					CN-DomainIdentity,
	cn-Type								CHOICE {
		gsm-MAP								NAS-SystemInformationGSM-MAP,
		ansi-41								NAS-SystemInformationANSI-41
	},
	cn-DRX-CycleLengthCoeff				CN-DRX-CycleLengthCoefficient
}

T-300 ::=							ENUMERATED {
										ms100, ms200, ms400, ms600, ms800,
										ms1000, ms1200, ms1400, ms1600,
										ms1800, ms2000, ms3000, ms4000,
										ms6000, ms8000 }

T-301 ::=							ENUMERATED {
										ms100, ms200, ms400, ms600, ms800,
										ms1000, ms1200, ms1400, ms1600,
										ms1800, ms2000, ms3000, ms4000,
										ms6000, ms8000, spare }

N-301 ::=							INTEGER (0..7)

N-302 ::=							INTEGER (0..7)

N-304 ::=							INTEGER (0..7)

N-308 ::=							INTEGER (1..8)

N-310 ::=							INTEGER (0..7)

T-302 ::=							ENUMERATED {
										ms100, ms200, ms400, ms600, ms800,
										ms1000, ms1200, ms1400, ms1600,
										ms1800, ms2000, ms3000, ms4000,
										ms6000, ms8000, spare }

T-304 ::=							ENUMERATED {
										ms100, ms200, ms400, 
										ms1000, ms2000, spare3, spare2, spare1 }

T-305 ::=							ENUMERATED {
										noUpdate, m5, m10, m30,
										m60, m120, m360, m720 }

T-307 ::=							ENUMERATED {
										s5, s10, s15, s20,
										s30, s40, s50, spare }

T-308 ::=							ENUMERATED {
										ms40, ms80, ms160, ms320 }

T-309 ::=							INTEGER (1..8)

T-310 ::=							ENUMERATED {
										ms40, ms80, ms120, ms160,
										ms200, ms240, ms280, ms320 }

T-311 ::=							ENUMERATED {
										ms250, ms500, ms750, ms1000,
										ms1250, ms1500, ms1750, ms2000 }

-- The value 0 for T-312 is not used in this version of the specification
T-312 ::=							INTEGER (0..15)

T-313 ::=							INTEGER (0..15)

T-314 ::=							ENUMERATED {
										s0, s2, s4, s6, s8,
										s12, s16, s20 }

T-315 ::=							ENUMERATED {
										s0, s10, s30, s60, s180,
										s600, s1200, s1800 }

T-316 ::=							ENUMERATED {
										s0, s10, s20, s30, s40,
										s50, s-inf, spare }

-- All the values are changed to "infinity" in Rel-5
T-317 ::=							ENUMERATED {
										infinity0,  infinity1,  infinity2, infinity3, infinity4,
										infinity5, infinity6, infinity7}

PDSCH-SysInfoList ::=				SEQUENCE (SIZE (1..maxPDSCH)) OF
										PDSCH-SysInfo

PDSCH-SysInfoList-HCR-r5 ::=			SEQUENCE (SIZE (1..maxPDSCH)) OF PDSCH-SysInfo-HCR-r5

PredefinedConfigIdentity ::=		INTEGER (0..15)

N-300 ::=							INTEGER (0..7)

N-312 ::=							ENUMERATED {
										s1, s50, s100, s200, s400,
										s600, s800, s1000 }

N-312ext ::=						ENUMERATED {
										s2, s4, s10, s20 }                                        

N-313 ::=							ENUMERATED {
										s1, s2, s4, s10, s20,
										 s50, s100, s200 }

N-315 ::=							ENUMERATED {
										s1, s50, s100, s200, s400,
										s600, s800, s1000 }

N-315ext ::=						ENUMERATED {
										s2, s4, s10, s20 }

URA-Identity ::=					BIT STRING (SIZE (16))

MappingInfo ::=						SEQUENCE (SIZE (1..maxRAT)) OF
										Mapping

Q-Hyst-S ::=						INTEGER (0..20)

S-SearchQual ::=						INTEGER (-16..10)

S-SearchRXLEV ::=						INTEGER (-53..45)

RAT-FDD-InfoList ::=				SEQUENCE (SIZE (1..maxOtherRAT)) OF
										RAT-FDD-Info


Q-QualMin ::=						INTEGER (-24..0)

Q-RxlevMin ::=						INTEGER (-58..-13)

RAT-TDD-InfoList ::=				SEQUENCE (SIZE (1..maxOtherRAT)) OF
										RAT-TDD-Info

T-Reselection-S ::=					INTEGER (0..31)                                        

HCS-ServingCellInformation ::=		SEQUENCE {
	hcs-PRIO							HCS-PRIO							DEFAULT 0,
	q-HCS								Q-HCS								DEFAULT 0,
	t-CR-Max							T-CRMax								OPTIONAL
}

MaxAllowedUL-TX-Power ::=			INTEGER (-50..33)

CellBarred ::=						CHOICE {
	barred								SEQUENCE {
		intraFreqCellReselectionInd			AllowedIndicator,
		t-Barred							T-Barred
	},
	notBarred							NULL
}

ReservedIndicator ::=				ENUMERATED {
										reserved,
										notReserved }

AccessClassBarredList ::=			SEQUENCE (SIZE (maxAC)) OF
										AccessClassBarred

MappingFunctionType ::=				ENUMERATED {
										linear,
										functionType2,
										functionType3,
										functionType4 }

MapParameter ::=					INTEGER (0..99)   

UpperLimit ::=						INTEGER (1..91)

DeltaQrxlevmin ::= INTEGER (-2..-1)

DeltaRSCP ::= INTEGER (-5..-1)

T-CRMax ::=							CHOICE {
	notUsed								NULL,
	t30									N-CR-T-CRMaxHyst,
	t60									N-CR-T-CRMaxHyst,
	t120								N-CR-T-CRMaxHyst,
	t180								N-CR-T-CRMaxHyst,
	t240								N-CR-T-CRMaxHyst
}

SpeedDependentScalingFactor ::=		INTEGER (0..10)

TreselectionScalingFactor ::=		INTEGER (4..19)

DomainSpecificAccessRestriction-v670ext ::= CHOICE {
		noRestriction		NULL,
		restriction			SEQUENCE {
			domainSpecficAccessClassBarredList		AccessClassBarredList	OPTIONAL
		}
}

DomainSpecificAccessRestrictionList-v670ext ::= SEQUENCE {
		domainSpecificAccessRestrictionParametersForOperator1
									DomainSpecificAccessRestrictionParam-v670ext	OPTIONAL,
		domainSpecificAccessRestrictionParametersForOperator2
									DomainSpecificAccessRestrictionParam-v670ext	OPTIONAL,
		domainSpecificAccessRestrictionParametersForOperator3
									DomainSpecificAccessRestrictionParam-v670ext	OPTIONAL,
		domainSpecificAccessRestrictionParametersForOperator4
									DomainSpecificAccessRestrictionParam-v670ext	OPTIONAL,
		domainSpecificAccessRestrictionParametersForOperator5
									DomainSpecificAccessRestrictionParam-v670ext	OPTIONAL
}

Q-Hyst-S-Fine ::= INTEGER (0..40)

T-Reselection-S-Fine ::=			INTEGER (0..31)

PUSCH-SysInfo ::=					SEQUENCE {
	pusch-Identity						PUSCH-Identity,
	pusch-Info							PUSCH-Info,
	usch-TFS							TransportFormatSet					OPTIONAL,
	usch-TFCS							TFCS								OPTIONAL
}

SFN-TimeInfo ::=					SEQUENCE {
	activationTimeSFN					INTEGER (0..4095),
	physChDuration					DurationTimeInfo
}

PrimaryCCPCH-TX-Power ::=			INTEGER (6..43)

Alpha ::=							INTEGER (0..8)

ConstantValueTdd ::=				INTEGER (-35..10)

TimeslotNumber ::=						INTEGER (0..14)

TimeslotSync2 ::=				INTEGER (0..6)

CellParametersID ::=				INTEGER (0..127)

PRACH-SystemInformation ::=			SEQUENCE {
	prach-RACH-Info						PRACH-RACH-Info,
	transportChannelIdentity			TransportChannelIdentity,
	rach-TransportFormatSet				TransportFormatSet					OPTIONAL,
	rach-TFCS							TFCS								OPTIONAL,
	prach-Partitioning					PRACH-Partitioning					OPTIONAL,
	persistenceScalingFactorList		PersistenceScalingFactorList		OPTIONAL,
	ac-To-ASC-MappingTable				AC-To-ASC-MappingTable				OPTIONAL,
	modeSpecificInfo					CHOICE {
		fdd									SEQUENCE {
			primaryCPICH-TX-Power				PrimaryCPICH-TX-Power		OPTIONAL,
			constantValue						ConstantValue				OPTIONAL,
			prach-PowerOffset					PRACH-PowerOffset			OPTIONAL,
			rach-TransmissionParameters			RACH-TransmissionParameters	OPTIONAL,
			aich-Info							AICH-Info					OPTIONAL
		},
		tdd									NULL
	}	
}

PRACH-SystemInformation-r7 ::=		SEQUENCE {
	prach-RACH-Info						PRACH-RACH-Info-r7,
	transportChannelIdentity			TransportChannelIdentity,
	rach-TransportFormatSet				TransportFormatSet					OPTIONAL,
	rach-TFCS							TFCS								OPTIONAL,
	prach-Partitioning					PRACH-Partitioning-r7				OPTIONAL,
	persistenceScalingFactorList		PersistenceScalingFactorList		OPTIONAL,
	ac-To-ASC-MappingTable				AC-To-ASC-MappingTable				OPTIONAL,
	modeSpecificInfo					CHOICE {
		fdd									SEQUENCE {
			primaryCPICH-TX-Power				PrimaryCPICH-TX-Power		OPTIONAL,
			constantValue						ConstantValue				OPTIONAL,
			prach-PowerOffset					PRACH-PowerOffset			OPTIONAL,
			rach-TransmissionParameters			RACH-TransmissionParameters	OPTIONAL,
			aich-Info							AICH-Info					OPTIONAL
		},
		tdd									NULL
	}
}

PRACH-SystemInformation-LCR-r4 ::=	SEQUENCE {
	prach-RACH-Info-LCR					PRACH-RACH-Info-LCR-r4,
	rach-TransportFormatSet-LCR			TransportFormatSet-LCR			OPTIONAL,
	prach-Partitioning-LCR				PRACH-Partitioning-LCR-r4		OPTIONAL
}

SCCPCH-SystemInformation ::=		SEQUENCE {
	secondaryCCPCH-Info					SecondaryCCPCH-Info,
	tfcs								TFCS								OPTIONAL,
	fach-PCH-InformationList			FACH-PCH-InformationList			OPTIONAL,
	pich-Info							PICH-Info							OPTIONAL
}

MaxPowerIncrease-r4 ::=				INTEGER (0..3)

SCCPCH-SystemInformation-LCR-r4-ext ::=	SEQUENCE {
	secondaryCCPCH-LCR-Extensions	SecondaryCCPCH-Info-LCR-r4-ext,
	-- pich-Info in the SCCPCH-SystemInformation IE shall be absent,
	-- and instead the following used.
	pich-Info						PICH-Info-LCR-r4						OPTIONAL
}

PUSCH-SysInfo-HCR-r5 ::=					SEQUENCE {
	pusch-Identity						PUSCH-Identity,
	pusch-Info							PUSCH-Info,
	usch-TransportChannelsInfo			USCH-TransportChannelsInfo			OPTIONAL,
	usch-TFCS							TFCS								OPTIONAL
}

RLC-Info-MCCH-r6 ::=				SEQUENCE {
	dl-UM-RLC-LI-size					DL-UM-RLC-LI-size,
	dl-UM-RLC-OutOSeqDelivery-Info		UM-RLC-OutOSeqDelivery-Info-r6		OPTIONAL
}

MBMS-TCTF-Presence ::=				ENUMERATED { false }

SecondaryCCPCHInfo-MBMS-r6 ::=		SEQUENCE {
	modeSpecificInfo				CHOICE {
		fdd								SEQUENCE {
			secondaryScramblingCode			SecondaryScramblingCode			OPTIONAL,
			sttd-Indicator					BOOLEAN,
			sf-AndCodeNumber				SF256-AndCodeNumber,
			timingOffset					TimingOffset					DEFAULT 0
		},
		tdd384							DownlinkTimeslotsCodes,
		tdd128							DownlinkTimeslotsCodes-LCR-r4
	}
}

TFCS ::=							CHOICE {
	normalTFCI-Signalling				ExplicitTFCS-Configuration,
	-- dummy is not used in this version of specification, it should
	-- not be sent and if received the UE behaviour is not specified.
	dummy								SplitTFCI-Signalling
}

TransportFormatSet ::=				CHOICE {
	dedicatedTransChTFS					DedicatedTransChTFS,
	commonTransChTFS					CommonTransChTFS
}

MBMS-FACHCarryingMTCH-List ::=		SEQUENCE (SIZE (1..maxFACHPCH)) OF
											TransportFormatSet

MBMS-MSCH-ConfigurationInfo-r6 ::=	SEQUENCE {
	mschShedulingInfo					MBMS-MSCHSchedulingInfo				OPTIONAL,
	rlc-Info							RLC-Info-MSCH-r6					OPTIONAL,
	tctf-Presence						MBMS-TCTF-Presence					OPTIONAL
}

AdditionalPRACH-TF-and-TFCS-CCCH-IEs ::= SEQUENCE {
	powerOffsetInformation				PowerOffsetInformation,
	dynamicTFInformationCCCH			DynamicTFInformationCCCH
}

PUSCH-SysInfo-LCR-r4 ::=			SEQUENCE {
	pusch-Identity						PUSCH-Identity,
	pusch-Info							PUSCH-Info-LCR-r4,
	usch-TFS							TransportFormatSet					OPTIONAL,
	usch-TFCS							TFCS								OPTIONAL
}

PDSCH-SysInfo-r7 ::=				SEQUENCE {
	pdsch-Identity						PDSCH-Identity,
	pdsch-Info							PDSCH-Info-r7,
	dsch-TransportChannelsInfo			DSCH-TransportChannelsInfo			OPTIONAL,
	dsch-TFCS							TFCS								OPTIONAL
}

SecondaryCCPCHInfo-MBMS-r7 ::=		SEQUENCE {
	modeSpecificInfo				CHOICE {
		fdd								SEQUENCE {
			secondaryScramblingCode			SecondaryScramblingCode			OPTIONAL,
			sttd-Indicator					BOOLEAN,
			sf-AndCodeNumber				SF256-AndCodeNumber,
			timingOffset					TimingOffset					DEFAULT 0
		},
		tdd384							DownlinkTimeslotsCodes,
		tdd768							DownlinkTimeslotsCodes-VHCR,
		tdd128							DownlinkTimeslotsCodes-LCR-r4
	}
}

AdditionalPRACH-TF-and-TFCS-CCCH ::=	SEQUENCE {
	additionalPRACH-TF-and-TFCS-CCCH-IEs	AdditionalPRACH-TF-and-TFCS-CCCH-IEs	OPTIONAL
}

PDSCH-SysInfo ::=					SEQUENCE {
	pdsch-Identity						PDSCH-Identity,
	pdsch-Info							PDSCH-Info,
	dsch-TFS							TransportFormatSet					OPTIONAL,
	dsch-TFCS							TFCS								OPTIONAL
}

PDSCH-SysInfo-HCR-r5 ::=					SEQUENCE {
	pdsch-Identity						PDSCH-Identity,
	pdsch-Info							PDSCH-Info,
	dsch-TransportChannelsInfo			DSCH-TransportChannelsInfo			OPTIONAL,
	dsch-TFCS							TFCS								OPTIONAL
}

PDSCH-SysInfo-LCR-r4 ::=			SEQUENCE {
	pdsch-Identity						PDSCH-Identity,
	pdsch-Info							PDSCH-Info-LCR-r4,
	dsch-TFS							TransportFormatSet					OPTIONAL,
	dsch-TFCS							TFCS								OPTIONAL
}

SCCPCH-SystemInformation-r7 ::=		SEQUENCE {
	secondaryCCPCH-Info					SecondaryCCPCH-Info-r7,
	tfcs								TFCS								OPTIONAL,
	fach-PCH-InformationList			FACH-PCH-InformationList			OPTIONAL,
	pich-Info							PICH-Info-r7						OPTIONAL
}

DynamicPersistenceLevel ::=			INTEGER (1..8)

InitialPriorityDelayList ::=		SEQUENCE (SIZE (1..maxASC)) OF
										NS-IP

                                        BackoffControlParams ::=			SEQUENCE {
	n-AP-RetransMax						N-AP-RetransMax,
	n-AccessFails						N-AccessFails,
	nf-BO-NoAICH						NF-BO-NoAICH,
	ns-BO-Busy							NS-BO-Busy,
	nf-BO-AllBusy						NF-BO-AllBusy,
	nf-BO-Mismatch						NF-BO-Mismatch,
	t-CPCH								T-CPCH
}

PowerControlAlgorithm ::=			CHOICE {
	algorithm1							TPC-StepSizeFDD,
	algorithm2							NULL
}

DL-DPCCH-BER ::=					INTEGER (0..63)

CPCH-SetInfo ::=					SEQUENCE {
	cpch-SetID							CPCH-SetID,
	transportFormatSet					TransportFormatSet,
	tfcs								TFCS,
	ap-PreambleScramblingCode			AP-PreambleScramblingCode,
	ap-AICH-ChannelisationCode			AP-AICH-ChannelisationCode,
	cd-PreambleScramblingCode			CD-PreambleScramblingCode,
	cd-CA-ICH-ChannelisationCode		CD-CA-ICH-ChannelisationCode,
	cd-AccessSlotSubchannelList			CD-AccessSlotSubchannelList			OPTIONAL,
	cd-SignatureCodeList				CD-SignatureCodeList				OPTIONAL,
	deltaPp-m							DeltaPp-m,
	ul-DPCCH-SlotFormat					UL-DPCCH-SlotFormat,
	n-StartMessage						N-StartMessage,
	n-EOT								N-EOT,
	-- TABULAR: VCAM info has been nested inside ChannelAssignmentActive,
	-- which in turn is mandatory since it's only a binary choice.
	channelAssignmentActive				ChannelAssignmentActive,
	cpch-StatusIndicationMode			CPCH-StatusIndicationMode,
	pcpch-ChannelInfoList				PCPCH-ChannelInfoList
}

CPCH-PersistenceLevels ::=			SEQUENCE {
	cpch-SetID							CPCH-SetID,
	dynamicPersistenceLevelTF-List		DynamicPersistenceLevelTF-List	
}

DRAC-SysInfo ::=					SEQUENCE {
	transmissionProbability				TransmissionProbability,
	maximumBitRate						MaximumBitRate
}

RAT-Type ::=						ENUMERATED {
										gsm, is2000 }

IntraFreqMeasurementSysInfo-RSCP ::=	SEQUENCE {
	intraFreqMeasurementID				MeasurementIdentity			DEFAULT 1,
	intraFreqCellInfoSI-List			IntraFreqCellInfoSI-List-RSCP		OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-ECN0 ::=		SEQUENCE {
	intraFreqMeasurementID				MeasurementIdentity			DEFAULT 1,
	intraFreqCellInfoSI-List			IntraFreqCellInfoSI-List-ECN0		OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

InterRATMeasurementSysInfo-B ::=	SEQUENCE {
	interRATCellInfoList				InterRATCellInfoList-B			OPTIONAL
}

IntraFreqMeasurementSysInfo-HCS-RSCP ::=	SEQUENCE {
	intraFreqMeasurementID				MeasurementIdentity			DEFAULT 1,
	intraFreqCellInfoSI-List			IntraFreqCellInfoSI-List-HCS-RSCP	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

IntraFreqMeasurementSysInfo-HCS-ECN0 ::=	SEQUENCE {
	intraFreqMeasurementID				MeasurementIdentity			DEFAULT 1,
	intraFreqCellInfoSI-List			IntraFreqCellInfoSI-List-HCS-ECN0	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH				OPTIONAL
}

InterRATMeasurementSysInfo ::=	SEQUENCE {
	interRATCellInfoList				InterRATCellInfoList				OPTIONAL
}

TrafficVolumeMeasSysInfo ::=		SEQUENCE {
	trafficVolumeMeasurementID			MeasurementIdentity			DEFAULT 4,
	trafficVolumeMeasurementObjectList	TrafficVolumeMeasurementObjectList	OPTIONAL,
	trafficVolumeMeasQuantity			TrafficVolumeMeasQuantity			OPTIONAL,
	trafficVolumeReportingQuantity		TrafficVolumeReportingQuantity		OPTIONAL,
	-- dummy is not used in this version of specification, it should
	-- not be sent and if received it should be ignored.
	dummy								TrafficVolumeReportingCriteria		OPTIONAL,
	measurementValidity					MeasurementValidity					OPTIONAL,
	measurementReportingMode			MeasurementReportingMode,
	reportCriteriaSysInf				TrafficVolumeReportCriteriaSysInfo

}

UE-InternalMeasurementSysInfo ::= 	SEQUENCE {
	ue-InternalMeasurementID			MeasurementIdentity			DEFAULT 5,
	ue-InternalMeasQuantity				UE-InternalMeasQuantity
}

IntraFreqMeasurementSysInfo-RSCP-LCR-r4 ::=	SEQUENCE {
	intraFreqMeasurementID				MeasurementIdentity			DEFAULT 1,
	intraFreqCellInfoSI-List			IntraFreqCellInfoSI-List-RSCP-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

InterFreqMeasurementSysInfo-ECN0-LCR-r4 ::=		SEQUENCE {
	interFreqCellInfoSI-List			InterFreqCellInfoSI-List-ECN0-LCR		OPTIONAL
}

IntraFreqMeasurementSysInfo-HCS-RSCP-LCR-r4 ::=	SEQUENCE {
	intraFreqMeasurementID				MeasurementIdentity			DEFAULT 1,
	intraFreqCellInfoSI-List			IntraFreqCellInfoSI-List-HCS-RSCP-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

InterFreqMeasurementSysInfo-HCS-ECN0-LCR-r4 ::=		SEQUENCE {
	interFreqCellInfoSI-List			InterFreqCellInfoSI-List-HCS-ECN0-LCR	OPTIONAL
}

InterFreqMeasurementSysInfo-RSCP ::=	SEQUENCE {
	interFreqCellInfoSI-List				InterFreqCellInfoSI-List-RSCP		OPTIONAL
}

InterFreqMeasurementSysInfo-ECN0 ::=		SEQUENCE {
	interFreqCellInfoSI-List			InterFreqCellInfoSI-List-ECN0		OPTIONAL
}

InterFreqMeasurementSysInfo-HCS-RSCP ::=		SEQUENCE {
	interFreqCellInfoSI-List			InterFreqCellInfoSI-List-HCS-RSCP	OPTIONAL
}

InterFreqMeasurementSysInfo-HCS-ECN0 ::=		SEQUENCE {
	interFreqCellInfoSI-List			InterFreqCellInfoSI-List-HCS-ECN0	OPTIONAL
}

InterFreqMeasurementSysInfo-RSCP-LCR-r4 ::=	SEQUENCE {
	interFreqCellInfoSI-List				InterFreqCellInfoSI-List-RSCP-LCR		OPTIONAL
}

IntraFreqMeasurementSysInfo-ECN0-LCR-r4 ::=		SEQUENCE {
	intraFreqMeasurementID				MeasurementIdentity			DEFAULT 1,
	intraFreqCellInfoSI-List			IntraFreqCellInfoSI-List-ECN0-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

InterFreqMeasurementSysInfo-HCS-RSCP-LCR-r4 ::=		SEQUENCE {
	interFreqCellInfoSI-List			InterFreqCellInfoSI-List-HCS-RSCP-LCR	OPTIONAL
}

IntraFreqMeasurementSysInfo-HCS-ECN0-LCR-r4 ::=	SEQUENCE {
	intraFreqMeasurementID				MeasurementIdentity			DEFAULT 1,
	intraFreqCellInfoSI-List			IntraFreqCellInfoSI-List-HCS-ECN0-LCR-r4	OPTIONAL,
	intraFreqMeasQuantity				IntraFreqMeasQuantity				OPTIONAL,
	intraFreqReportingQuantityForRACH	IntraFreqReportingQuantityForRACH	OPTIONAL,
	maxReportedCellsOnRACH				MaxReportedCellsOnRACH				OPTIONAL,
	reportingInfoForCellDCH				ReportingInfoForCellDCH-LCR-r4		OPTIONAL
}

PeriodicReportingInfo-1b ::= SEQUENCE {
	reportingAmount						ReportingAmount,
	reportingInterval					ReportingInterval
}

TriggeringCondition2 ::=			ENUMERATED {
										activeSetCellsOnly,
										monitoredSetCellsOnly,
										activeSetAndMonitoredSetCells,
										detectedSetCellsOnly,
										detectedSetAndMonitoredSetCells }

InterFreqRepQuantityRACH-FDD ::=	ENUMERATED {
										cpich-EcN0, cpich-RSCP }

InterFreqRepQuantityRACH-TDDList ::= SEQUENCE (SIZE (1..2)) OF
										InterFreqRepQuantityRACH-TDD

Threshold ::=						INTEGER (-115..0)

MaxReportedCellsOnRACHinterFreq ::=		INTEGER (1..8)


SystemSpecificCapUpdateReqList ::= SEQUENCE (SIZE (1..maxSystemCapability)) OF 
										SystemSpecificCapUpdateReq

SystemSpecificCapUpdateReq ::=		ENUMERATED {
										gsm }      

IndividualTS-Interference ::=		SEQUENCE {
	timeslot							TimeslotNumber,
	ul-TimeslotInterference				TDD-UL-Interference
}

EllipsoidPointAltitudeEllipsoide ::=	SEQUENCE {
	latitudeSign			ENUMERATED { north, south },
	latitude				INTEGER (0..8388607),
	longitude				INTEGER (-8388608..8388607),
	altitudeDirection		ENUMERATED {height, depth},
	altitude				INTEGER (0..32767),
	uncertaintySemiMajor	INTEGER (0..127),
	uncertaintySemiMinor	INTEGER (0..127),
	-- Actual value orientationMajorAxis = IE value * 2
	orientationMajorAxis	INTEGER (0..89),
	uncertaintyAltitude		INTEGER (0..127),
	confidence				INTEGER (0..100)
}

GPS-TOW-1msec ::=					INTEGER (0..604799999)

UTRAN-GPSReferenceTime ::=				SEQUENCE {
	-- For utran-GPSTimingOfCell values above 2322431999999 are not 
	-- used in this version of the specification
	-- Actual value utran-GPSTimingOfCell = (ms-part * 4294967296) + ls-part
	utran-GPSTimingOfCell			SEQUENCE {
		ms-part 						INTEGER (0..1023),
		ls-part							INTEGER (0..4294967295)
	},
	modeSpecificInfo				CHOICE {
		fdd								SEQUENCE {
			referenceIdentity				PrimaryCPICH-Info
		},
		tdd								SEQUENCE {
			referenceIdentity				CellParametersID
		}
	} 				OPTIONAL,
	sfn									INTEGER (0..4095)
}

FN-TOW-Uncertainty ::=				ENUMERATED {
										lessThan10,
										moreThan10 }

UTRAN-GPS-DriftRate ::=				ENUMERATED {
									utran-GPSDrift0, utran-GPSDrift1, utran-GPSDrift2,
									utran-GPSDrift5, utran-GPSDrift10, utran-GPSDrift15,
									utran-GPSDrift25, utran-GPSDrift50, utran-GPSDrift-1,
									utran-GPSDrift-2, utran-GPSDrift-5, utran-GPSDrift-10,
									utran-GPSDrift-15, utran-GPSDrift-25, utran-GPSDrift-50}

GPS-TOW-AssistList ::=				SEQUENCE (SIZE (1..maxSat)) OF
										GPS-TOW-Assist                                        

IP-Spacing-TDD ::=						ENUMERATED {
										e30, e40, e50, e70, e100}

IP-PCCPCH-r4 ::=					BOOLEAN

BurstModeParameters ::=				SEQUENCE {
	burstStart							INTEGER (0..15),
	burstLength							INTEGER (10..25),
	burstFreq							INTEGER (1..16)
}

DiffCorrectionStatus ::=			ENUMERATED {
										udre-1-0, udre-0-75, udre-0-5, udre-0-3,
										udre-0-2, udre-0-1, noData, invalidData }

DGPS-CorrectionSatInfoList ::=		SEQUENCE (SIZE (1..maxSat)) OF
										DGPS-CorrectionSatInfo

SubFrame1Reserved ::= 				SEQUENCE {
 	reserved1							BIT STRING (SIZE (23)),
	reserved2							BIT STRING (SIZE (24)),
	reserved3							BIT STRING (SIZE (24)),
	reserved4							BIT STRING (SIZE (16))
}

AlmanacSatInfoList ::=				SEQUENCE (SIZE (1..maxSat)) OF
										AlmanacSatInfo

UE-Positioning-OTDOA-ReferenceCellInfo ::=			SEQUENCE {
	sfn									INTEGER (0..4095)									OPTIONAL,
	modeSpecificInfo CHOICE {
		fdd										SEQUENCE {
			primaryCPICH-Info					PrimaryCPICH-Info
		},
		tdd										SEQUENCE{
			cellAndChannelIdentity				CellAndChannelIdentity
		}
	},
	frequencyInfo						FrequencyInfo						OPTIONAL,
	positioningMode CHOICE {
		ueBased									SEQUENCE {},
		ueAssisted								SEQUENCE {}
	},
	ue-positioning-IPDL-Paremeters				UE-Positioning-IPDL-Parameters	OPTIONAL
}

UE-Positioning-OTDOA-NeighbourCellList ::= SEQUENCE (SIZE (1..maxCellMeas)) OF
											UE-Positioning-OTDOA-NeighbourCellInfo

UE-Positioning-IPDL-Parameters-TDDList-r4-ext ::=	SEQUENCE (SIZE (1..maxCellMeas)) OF
											UE-Positioning-IPDL-Parameters-TDD-r4-ext

UE-Positioning-OTDOA-ReferenceCellInfo-UEB ::=			SEQUENCE {
	sfn									INTEGER (0..4095)					OPTIONAL,
	modeSpecificInfo CHOICE {
		fdd										SEQUENCE {
			primaryCPICH-Info					PrimaryCPICH-Info
		},
		tdd										SEQUENCE{
			cellAndChannelIdentity				CellAndChannelIdentity
		}
	},
	frequencyInfo						FrequencyInfo						OPTIONAL,
	cellPosition						ReferenceCellPosition				OPTIONAL,
	-- actual value roundTripTime = (IE value * 0.0625) + 876
	roundTripTime						INTEGER (0..32766)					OPTIONAL,
	ue-positioning-IPDL-Paremeters		UE-Positioning-IPDL-Parameters		OPTIONAL
}

PredefinedRB-Configuration ::=		SEQUENCE {
	re-EstablishmentTimer				Re-EstablishmentTimer,
	srb-InformationList					SRB-InformationSetupList,
	rb-InformationList					RB-InformationSetupList
}

PreDefTransChConfiguration ::=		SEQUENCE {
	ul-CommonTransChInfo				UL-CommonTransChInfo,
	ul-AddReconfTrChInfoList			UL-AddReconfTransChInfoList,
	dl-CommonTransChInfo				DL-CommonTransChInfo,
	dl-TrChInfoList						DL-AddReconfTransChInfoList
}

PreDefPhyChConfiguration ::=		SEQUENCE {
	ul-DPCH-InfoPredef					UL-DPCH-InfoPredef,
	dl-CommonInformationPredef			DL-CommonInformationPredef	OPTIONAL
}

PLMNsOfIntraFreqCellsList ::=			SEQUENCE (SIZE (1..maxCellMeas)) OF
											SEQUENCE {
	plmn-Identity								PLMN-Identity				OPTIONAL
}

PLMNsOfInterRATCellsList ::=			SEQUENCE (SIZE (1..maxCellMeas)) OF
											SEQUENCE {
	plmn-Identity								PLMN-Identity				OPTIONAL
}

SchedulingInformationSIB ::=			SEQUENCE {
	sib-Type							SIB-TypeAndTag,
	scheduling							SchedulingInformation
}

UARFCN ::=						INTEGER (0..16383)

SFN-TOW-Uncertainty ::=				ENUMERATED {
										lessThan10,
										moreThan10 }

UE-Positioning-OTDOA-NeighbourCellList-UEB ::= SEQUENCE (SIZE (1..maxCellMeas)) OF
											UE-Positioning-OTDOA-NeighbourCellInfo-UEB

PLMNsOfInterFreqCellsList ::=			SEQUENCE (SIZE (1..maxCellMeas)) OF
											SEQUENCE {
	plmn-Identity								PLMN-Identity				OPTIONAL
}

CN-DomainIdentity ::=				ENUMERATED {
										cs-domain,
										ps-domain }

NAS-SystemInformationANSI-41 ::=		ANSI-41-NAS-Parameter

CN-DRX-CycleLengthCoefficient ::=	INTEGER (6..9)

Mapping ::=							SEQUENCE {
	rat									RAT,
	mappingFunctionParameterList		MappingFunctionParameterList
}

RAT-FDD-Info ::=					SEQUENCE {
	rat-Identifier						RAT-Identifier,
	s-SearchRAT							S-SearchQual,
	s-HCS-RAT							S-SearchRXLEV							OPTIONAL,
	s-Limit-SearchRAT					S-SearchQual
}

RAT-TDD-Info ::=					SEQUENCE {
	rat-Identifier						RAT-Identifier,
	s-SearchRAT							S-SearchRXLEV,
	s-HCS-RAT							S-SearchRXLEV						OPTIONAL,
	s-Limit-SearchRAT					S-SearchRXLEV
}

HCS-PRIO ::=						INTEGER (0..7)

Q-HCS ::=							INTEGER (0..99)

AllowedIndicator ::=				ENUMERATED {
										allowed, notAllowed }

T-Barred ::=						ENUMERATED {
										s10, s20, s40, s80,
										s160, s320, s640, s1280 }

AccessClassBarred ::=				ENUMERATED {
										barred, notBarred }

N-CR-T-CRMaxHyst ::=				SEQUENCE {
	n-CR								INTEGER (1..16)						DEFAULT 8,
	t-CRMaxHyst							T-CRMaxHyst
}

PUSCH-Identity ::=					INTEGER (1..hiPUSCHidentities)

PUSCH-Info ::=						SEQUENCE {
	tfcs-ID								TFCS-IdentityPlain					DEFAULT 1,
	commonTimeslotInfo					CommonTimeslotInfo					OPTIONAL,
	pusch-TimeslotsCodes				UplinkTimeslotsCodes				OPTIONAL
}

DurationTimeInfo ::=				INTEGER (1..4096)

PRACH-RACH-Info ::=					SEQUENCE {
	modeSpecificInfo					CHOICE {
		fdd									SEQUENCE {
			availableSignatures					AvailableSignatures,
			availableSF							SF-PRACH,
			preambleScramblingCodeWordNumber	PreambleScramblingCodeWordNumber,
			puncturingLimit						PuncturingLimit,
			availableSubChannelNumbers			AvailableSubChannelNumbers
		},
		tdd									SEQUENCE {
			timeslot							TimeslotNumber,
			channelisationCodeList				TDD-PRACH-CCodeList,
			prach-Midamble						PRACH-Midamble
		}
	}
}

TransportChannelIdentity ::=		INTEGER (1..32)

PRACH-Partitioning ::=				CHOICE {
	fdd									SEQUENCE (SIZE (1..maxASC)) OF
	-- TABULAR: If only "NumASC+1" (with, NumASC+1 < maxASC) ASCSetting-FDD are listed, 
	-- the remaining (NumASC+2 through maxASC) ASCs are unspecified.
											ASCSetting-FDD,
	tdd									SEQUENCE (SIZE (1..maxASC)) OF
	-- TABULAR: If only "NumASC+1" (with, NumASC+1 < maxASC) ASCSetting-TDD are listed, 
	-- the remaining (NumASC+2 through maxASC) ASCs are unspecified.
											ASCSetting-TDD
}	

PersistenceScalingFactorList ::=	SEQUENCE (SIZE (1..maxASCpersist)) OF
										PersistenceScalingFactor

AC-To-ASC-MappingTable ::=			SEQUENCE (SIZE (maxASCmap)) OF
										AC-To-ASC-Mapping

PrimaryCPICH-TX-Power ::=			INTEGER (-10..50)

ConstantValue ::=					INTEGER (-35..-10)

PRACH-PowerOffset ::=				SEQUENCE {
	powerRampStep						PowerRampStep,
	preambleRetransMax					PreambleRetransMax
}

RACH-TransmissionParameters ::=		SEQUENCE {
	mmax								INTEGER (1..32),
	nb01Min								NB01,
	nb01Max								NB01
}

AICH-Info ::=						SEQUENCE {
	channelisationCode256				ChannelisationCode256,
	sttd-Indicator						BOOLEAN,
	aich-TransmissionTiming				AICH-TransmissionTiming
}

PRACH-RACH-Info-r7 ::=				SEQUENCE {
	modeSpecificInfo					CHOICE {
		fdd									SEQUENCE {
			availableSignatures					AvailableSignatures,
			availableSF							SF-PRACH,
			preambleScramblingCodeWordNumber	PreambleScramblingCodeWordNumber,
			puncturingLimit						PuncturingLimit,
			availableSubChannelNumbers			AvailableSubChannelNumbers
		},
		tdd384									SEQUENCE {
			timeslot							TimeslotNumber,
			channelisationCodeList				TDD-PRACH-CCodeList,
			prach-Midamble						PRACH-Midamble
		},
		tdd768									SEQUENCE {
			timeslot							TimeslotNumber,
			channelisationCodeList				TDD768-PRACH-CCodeList,
			prach-Midamble						PRACH-Midamble
		}
	}
}

PRACH-Partitioning-r7 ::=			CHOICE {
	fdd									SEQUENCE (SIZE (1..maxASC)) OF
	-- TABULAR: If only "NumASC+1" (with, NumASC+1 < maxASC) ASCSetting-FDD are listed,
	-- the remaining (NumASC+2 through maxASC) ASCs are unspecified.
											ASCSetting-FDD,
	tdd									SEQUENCE (SIZE (1..maxASC)) OF
	-- TABULAR: If only "NumASC+1" (with, NumASC+1 < maxASC) ASCSetting-TDD are listed,
	-- the remaining (NumASC+2 through maxASC) ASCs are unspecified.
											ASCSetting-TDD-r7
}

PRACH-RACH-Info-LCR-r4 ::=			SEQUENCE {
	sync-UL-Info						SYNC-UL-Info-r4,
	prach-DefinitionList				SEQUENCE (SIZE (1..maxPRACH-FPACH)) OF
											PRACH-Definition-LCR-r4
}

TransportFormatSet-LCR ::=				CHOICE {
	dedicatedTransChTFS					DedicatedTransChTFS,
	commonTransChTFS-LCR				CommonTransChTFS-LCR
}

PRACH-Partitioning-LCR-r4 ::=		SEQUENCE (SIZE (1..maxASC)) OF
	-- TABULAR: If only "NumASC+1" (with, NumASC+1 < maxASC) ASCSetting-TDD-LCR-r4 are listed, 
	-- the remaining (NumASC+2 through maxASC) ASCs are unspecified.
											ASCSetting-TDD-LCR-r4

SecondaryCCPCH-Info ::=				SEQUENCE {
	modeSpecificInfo				CHOICE {
		fdd								SEQUENCE {
			-- dummy1 is not used in this version of the specification and should be ignored.
			dummy1							PCPICH-UsageForChannelEst,
			-- dummy2 is not used in this version of the specification.  It should not
			-- be sent and if received it should be ignored.
			dummy2							SecondaryCPICH-Info				OPTIONAL,
			secondaryScramblingCode			SecondaryScramblingCode			OPTIONAL,
			sttd-Indicator					BOOLEAN,
			sf-AndCodeNumber				SF256-AndCodeNumber,
			pilotSymbolExistence			BOOLEAN,
			tfci-Existence					BOOLEAN,
			positionFixedOrFlexible			PositionFixedOrFlexible,
			timingOffset					TimingOffset					DEFAULT 0
		},
		tdd 							SEQUENCE {
			-- TABULAR: the offset is included in CommonTimeslotInfoSCCPCH
			commonTimeslotInfo				CommonTimeslotInfoSCCPCH,
			individualTimeslotInfo			IndividualTimeslotInfo,
			channelisationCode				SCCPCH-ChannelisationCodeList
		}
	}
}

FACH-PCH-InformationList ::=		SEQUENCE (SIZE (1..maxFACHPCH)) OF
										FACH-PCH-Information

PICH-Info ::=						CHOICE {
	fdd									SEQUENCE {
		channelisationCode256				ChannelisationCode256,
		pi-CountPerFrame					PI-CountPerFrame,
		sttd-Indicator						BOOLEAN
	},
	tdd									SEQUENCE {
		channelisationCode					TDD-PICH-CCode					OPTIONAL,
		timeslot							TimeslotNumber					OPTIONAL,
		midambleShiftAndBurstType			MidambleShiftAndBurstType,
		repetitionPeriodLengthOffset		RepPerLengthOffset-PICH			OPTIONAL,
		pagingIndicatorLength				PagingIndicatorLength			DEFAULT pi4,
		n-GAP								N-GAP							DEFAULT f4,
		n-PCH								N-PCH							DEFAULT 2
	}	
}

SecondaryCCPCH-Info-LCR-r4-ext ::=	SEQUENCE {
	individualTimeslotLCR-Ext			IndividualTimeslotInfo-LCR-r4-ext
}

PICH-Info-LCR-r4 ::=				SEQUENCE {
	timeslot							TimeslotNumber-LCR-r4				OPTIONAL,
	pichChannelisationCodeList-LCR-r4	PichChannelisationCodeList-LCR-r4,
	midambleShiftAndBurstType			MidambleShiftAndBurstType-LCR-r4,
	repetitionPeriodLengthOffset		RepPerLengthOffset-PICH				OPTIONAL,
	pagingIndicatorLength				PagingIndicatorLength			DEFAULT pi4,
	n-GAP								N-GAP							DEFAULT f4,
	n-PCH								N-PCH							DEFAULT 2
}

USCH-TransportChannelsInfo ::=		SEQUENCE (SIZE (1..maxTrCH)) OF
										SEQUENCE {
	usch-TransportChannelIdentity			TransportChannelIdentity,
	usch-TFS								TransportFormatSet
}

DL-UM-RLC-LI-size ::=					ENUMERATED {
										size7, size15 }

UM-RLC-OutOSeqDelivery-Info-r6 ::=	SEQUENCE {
	timer-OSD							TimerOSD-r6							OPTIONAL,
	windowSize-OSD						WindowSizeOSD-r6
}

SecondaryScramblingCode ::=			INTEGER (1..15)

SF256-AndCodeNumber ::=				CHOICE {
	sf4									INTEGER (0..3),
	sf8									INTEGER (0..7),
	sf16								INTEGER (0..15),
	sf32								INTEGER (0..31),
	sf64								INTEGER (0..63),
	sf128								INTEGER (0..127),
	sf256								INTEGER (0..255)
}

TimingOffset ::=					INTEGER (0..149)

DownlinkTimeslotsCodes ::=		SEQUENCE {
	firstIndividualTimeslotInfo			IndividualTimeslotInfo,
	dl-TS-ChannelisationCodesShort		DL-TS-ChannelisationCodesShort,
	moreTimeslots						CHOICE {
		noMore								NULL,
		additionalTimeslots					CHOICE {
			consecutive							INTEGER (1..maxTS-1),
			timeslotList						SEQUENCE (SIZE (1..maxTS-1)) OF
													DownlinkAdditionalTimeslots
		}
	}
}

DownlinkTimeslotsCodes-LCR-r4 ::=	SEQUENCE {
	firstIndividualTimeslotInfo			IndividualTimeslotInfo-LCR-r4,
	dl-TS-ChannelisationCodesShort		DL-TS-ChannelisationCodesShort,
	moreTimeslots						CHOICE {
		noMore								NULL,
		additionalTimeslots					CHOICE {
			consecutive							INTEGER (1..maxTS-LCR-1),
			timeslotList						SEQUENCE (SIZE (1..maxTS-LCR-1)) OF
													DownlinkAdditionalTimeslots-LCR-r4
		}
	}
}

ExplicitTFCS-Configuration ::=		CHOICE {
	complete							TFCS-ReconfAdd,
	addition							TFCS-ReconfAdd,
	removal								TFCS-RemovalList,
	replacement							SEQUENCE {
		tfcsRemoval							TFCS-RemovalList,
		tfcsAdd								TFCS-ReconfAdd
	}
}

SplitTFCI-Signalling ::=			SEQUENCE {
	splitType							SplitType						OPTIONAL,
	tfci-Field2-Length					INTEGER (1..10)					OPTIONAL,
	tfci-Field1-Information				ExplicitTFCS-Configuration		OPTIONAL,
	tfci-Field2-Information				TFCI-Field2-Information			OPTIONAL
}

DedicatedTransChTFS ::=				SEQUENCE {
	tti									CHOICE {
		tti10								DedicatedDynamicTF-InfoList,
		tti20								DedicatedDynamicTF-InfoList,
		tti40								DedicatedDynamicTF-InfoList,
		tti80								DedicatedDynamicTF-InfoList,
		dynamic								DedicatedDynamicTF-InfoList-DynamicTTI
	},
	semistaticTF-Information			SemistaticTF-Information
}

CommonTransChTFS ::=				SEQUENCE {
	tti									CHOICE {
		tti10								CommonDynamicTF-InfoList,
		tti20								CommonDynamicTF-InfoList,
		tti40								CommonDynamicTF-InfoList,
		tti80								CommonDynamicTF-InfoList,
		dynamic								CommonDynamicTF-InfoList-DynamicTTI
	},
	semistaticTF-Information			SemistaticTF-Information
}

MBMS-MSCHSchedulingInfo ::=			CHOICE {
	schedulingPeriod-32-Offset			INTEGER (0..31),
	schedulingPeriod-64-Offset			INTEGER (0..63),
	schedulingPeriod-128-Offset			INTEGER (0..127),
	schedulingPeriod-256-Offset			INTEGER (0..255),
	schedulingPeriod-512-Offset			INTEGER (0..511),
	schedulingPeriod-1024-Offset		INTEGER (0..1023)
}

RLC-Info-MSCH-r6 ::=				SEQUENCE {
	dl-UM-RLC-LI-size					DL-UM-RLC-LI-size
}

PowerOffsetInformation ::=			SEQUENCE {
	gainFactorInformation				GainFactorInformation,
	-- PowerOffsetPp-m is always absent in TDD
	powerOffsetPp-m						PowerOffsetPp-m						OPTIONAL
}

DynamicTFInformationCCCH ::=		SEQUENCE {
	octetModeRLC-SizeInfoType2			OctetModeRLC-SizeInfoType2
}

PUSCH-Info-VHCR ::=					SEQUENCE {
	tfcs-ID								TFCS-IdentityPlain					DEFAULT 1,
	commonTimeslotInfo					CommonTimeslotInfo					OPTIONAL,
	pusch-TimeslotsCodes-VHCR			UplinkTimeslotsCodes-VHCR			OPTIONAL
}

PUSCH-SysInfo-VHCR ::=					SEQUENCE {
	pusch-Identity						PUSCH-Identity,
	pusch-Info-VHCR						PUSCH-Info-VHCR,
	usch-TransportChannelsInfo			USCH-TransportChannelsInfo			OPTIONAL,
	usch-TFCS							TFCS								OPTIONAL
}

PUSCH-Info-LCR-r4 ::=				SEQUENCE {
	tfcs-ID								TFCS-IdentityPlain					DEFAULT 1,

	commonTimeslotInfo					CommonTimeslotInfo					OPTIONAL,
	pusch-TimeslotsCodes				UplinkTimeslotsCodes-LCR-r4			OPTIONAL
}

PDSCH-Identity ::=					INTEGER (1..hiPDSCHidentities)

PDSCH-Info-r7 ::=						SEQUENCE {
	tfcs-ID								TFCS-IdentityPlain					DEFAULT 1,
	commonTimeslotInfo					CommonTimeslotInfo					OPTIONAL,
	tddOption							CHOICE {
		tdd384								SEQUENCE {
			pdsch-TimeslotsCodes				DownlinkTimeslotsCodes		OPTIONAL
		},
		tdd768								SEQUENCE {
			pdsch-TimeslotsCodes				DownlinkTimeslotsCodes-VHCR		OPTIONAL
		},
		tdd128								SEQUENCE {
			pdsch-TimeslotsCodes				DownlinkTimeslotsCodes-LCR-r4	OPTIONAL
		}
	}
}

DSCH-TransportChannelsInfo ::=		SEQUENCE (SIZE (1..maxTrCH)) OF
										SEQUENCE {
	dsch-transport-channel-identity			TransportChannelIdentity,
	dsch-TFS								TransportFormatSet
}

DownlinkTimeslotsCodes-VHCR ::=		SEQUENCE {
	firstIndividualTimeslotInfo			IndividualTimeslotInfo-VHCR,
	dl-TS-ChannelisationCodesShort		DL-TS-ChannelisationCodesShort,
	moreTimeslots						CHOICE {
		noMore								NULL,
		additionalTimeslots					CHOICE {
			consecutive							INTEGER (1..maxTS-1),
			timeslotList						SEQUENCE (SIZE (1..maxTS-1)) OF
													DownlinkAdditionalTimeslots-VHCR
		}
	}
}

PDSCH-Info ::=						SEQUENCE {
	tfcs-ID								TFCS-IdentityPlain					DEFAULT 1,
	commonTimeslotInfo					CommonTimeslotInfo					OPTIONAL,
	pdsch-TimeslotsCodes				DownlinkTimeslotsCodes				OPTIONAL
}

PDSCH-Info-LCR-r4 ::=				SEQUENCE {
	tfcs-ID								TFCS-IdentityPlain					DEFAULT 1,
	commonTimeslotInfo					CommonTimeslotInfo					OPTIONAL,
	pdsch-TimeslotsCodes				DownlinkTimeslotsCodes-LCR-r4		OPTIONAL
}

SecondaryCCPCH-Info-r7 ::=		SEQUENCE {
	modeSpecificInfo				CHOICE {
		fdd								SEQUENCE {
			secondaryScramblingCode			SecondaryScramblingCode			OPTIONAL,
			sttd-Indicator					BOOLEAN,
			sf-AndCodeNumber				SF256-AndCodeNumber,
			pilotSymbolExistence			BOOLEAN,
			tfci-Existence					BOOLEAN,
			positionFixedOrFlexible			PositionFixedOrFlexible,
			timingOffset					TimingOffset					DEFAULT 0
		},
		tdd 							SEQUENCE {
			-- TABULAR: the offset is included in CommonTimeslotInfoSCCPCH
			commonTimeslotInfo				CommonTimeslotInfoSCCPCH,
			tddOption						CHOICE {
				tdd384							SEQUENCE {
					individualTimeslotInfo			IndividualTimeslotInfo,
					channelisationCode				SCCPCH-ChannelisationCodeList
				},
				tdd768							SEQUENCE {
					individualTimeslotInfo			IndividualTimeslotInfo-VHCR,
					channelisationCode				SCCPCH-ChannelisationCodeList-VHCR
				},
				tdd128							SEQUENCE {
					individualTimeslotInfo			IndividualTimeslotInfo-LCR-r4,
					channelisationCode				SCCPCH-ChannelisationCodeList
				}
			}
		}
	}
}

PICH-Info-r7 ::=					CHOICE {
	fdd									SEQUENCE {
		channelisationCode256				ChannelisationCode256,
		pi-CountPerFrame					PI-CountPerFrame,
		sttd-Indicator						BOOLEAN
	},
	tdd384									SEQUENCE {
		channelisationCode					TDD-PICH-CCode					OPTIONAL,
		timeslot							TimeslotNumber					OPTIONAL,
		midambleShiftAndBurstType			MidambleShiftAndBurstType,
		repetitionPeriodLengthOffset		RepPerLengthOffset-PICH			OPTIONAL,
		pagingIndicatorLength				PagingIndicatorLength			DEFAULT pi4,
		n-GAP								N-GAP							DEFAULT f4,
		n-PCH								N-PCH							DEFAULT 2
	},
	tdd768									SEQUENCE {
		channelisationCode					TDD768-PICH-CCode				OPTIONAL,
		timeslot							TimeslotNumber					OPTIONAL,
		midambleShiftAndBurstType			MidambleShiftAndBurstType,
		repetitionPeriodLengthOffset		RepPerLengthOffset-PICH			OPTIONAL,
		pagingIndicatorLength				PagingIndicatorLength			DEFAULT pi4,
		n-GAP								N-GAP							DEFAULT f4,
		n-PCH								N-PCH							DEFAULT 2
	}
}

NS-IP ::=							INTEGER (0..28)

N-AP-RetransMax ::=					INTEGER (1..64)

N-AccessFails ::=					INTEGER (1..64)

NF-BO-NoAICH ::=					INTEGER (0..31)

NS-BO-Busy ::=						INTEGER (0..63)

NF-BO-AllBusy ::=					INTEGER (0..31)

NF-BO-Mismatch ::=					INTEGER (0..127)

T-CPCH ::=							ENUMERATED {
										ct0, ct1 }

TPC-StepSizeFDD ::=					INTEGER (0..1)	

CPCH-SetID ::=						INTEGER (1..maxCPCHsets)

AP-AICH-ChannelisationCode ::=		INTEGER (0..255)

AP-PreambleScramblingCode ::=		INTEGER (0..79)

CD-PreambleScramblingCode ::=		INTEGER (0..79)

CD-CA-ICH-ChannelisationCode ::=	INTEGER (0..255)

CD-AccessSlotSubchannel ::=			INTEGER (0..11)

CD-AccessSlotSubchannelList ::=		SEQUENCE (SIZE (1..maxPCPCH-CDsubCh)) OF
										CD-AccessSlotSubchannel

CD-SignatureCode ::=				INTEGER (0..15)

CD-SignatureCodeList ::=			SEQUENCE (SIZE (1..maxPCPCH-CDsig)) OF
										CD-SignatureCode

DeltaPp-m ::=						INTEGER (-10..10)

UL-DPCCH-SlotFormat ::=				ENUMERATED {
										slf0, slf1, slf2 }

N-StartMessage ::=					INTEGER (1..8)		

N-EOT ::=							INTEGER (0..7)	

ChannelAssignmentActive ::=			CHOICE {
	notActive							NULL,
	isActive							AvailableMinimumSF-ListVCAM
}

CPCH-StatusIndicationMode ::=		ENUMERATED {
										pa-mode,
										pamsf-mode }

PCPCH-ChannelInfoList ::=			SEQUENCE (SIZE (1..maxPCPCHs)) OF
										PCPCH-ChannelInfo										

DynamicPersistenceLevelTF-List ::= SEQUENCE (SIZE (1..maxTF-CPCH)) OF
										DynamicPersistenceLevel

TransmissionProbability ::=			INTEGER (1..8)

MaximumBitRate ::=					INTEGER (0..32)

MeasurementIdentity ::=		INTEGER (1..16)

IntraFreqCellInfoSI-List-RSCP ::=	SEQUENCE {
	removedIntraFreqCellList			RemovedIntraFreqCellList			OPTIONAL,
	newIntraFreqCellList				NewIntraFreqCellSI-List-RSCP
}

IntraFreqMeasQuantity ::=			SEQUENCE {
	filterCoefficient					FilterCoefficient					DEFAULT fc0,
	modeSpecificInfo 					CHOICE {
		fdd								SEQUENCE {
			intraFreqMeasQuantity-FDD		IntraFreqMeasQuantity-FDD
		},
		tdd								SEQUENCE {
			intraFreqMeasQuantity-TDDList	IntraFreqMeasQuantity-TDDList
		}
	}
}

IntraFreqReportingQuantityForRACH ::= SEQUENCE {
	sfn-SFN-OTD-Type					SFN-SFN-OTD-Type,
	modeSpecificInfo					CHOICE {
		fdd									SEQUENCE {
			intraFreqRepQuantityRACH-FDD		IntraFreqRepQuantityRACH-FDD
		},
		tdd									SEQUENCE {
			intraFreqRepQuantityRACH-TDDList	IntraFreqRepQuantityRACH-TDDList
		}
	}
}

MaxReportedCellsOnRACH ::=			ENUMERATED {
										noReport,
										currentCell,
										currentAnd-1-BestNeighbour,
										currentAnd-2-BestNeighbour,
										currentAnd-3-BestNeighbour,
										currentAnd-4-BestNeighbour,
										currentAnd-5-BestNeighbour,
										currentAnd-6-BestNeighbour }

ReportingInfoForCellDCH ::=			SEQUENCE {
	intraFreqReportingQuantity			IntraFreqReportingQuantity,
	measurementReportingMode			MeasurementReportingMode,
	reportCriteria						CellDCH-ReportCriteria
}

IntraFreqCellInfoSI-List-ECN0 ::=		SEQUENCE {
	removedIntraFreqCellList			RemovedIntraFreqCellList			OPTIONAL,
	newIntraFreqCellList				NewIntraFreqCellSI-List-ECN0
}

InterRATCellInfoList-B ::=			SEQUENCE {
	removedInterRATCellList			RemovedInterRATCellList,
	-- NOTE: IE newInterRATCellList should be optional.  However, system information
	-- does not support message versions.  Hence, this can not be corrected
	newInterRATCellList				NewInterRATCellList-B
}

IntraFreqCellInfoSI-List-HCS-RSCP ::=		SEQUENCE {
	removedIntraFreqCellList			RemovedIntraFreqCellList			OPTIONAL,
	newIntraFreqCellList				NewIntraFreqCellSI-List-HCS-RSCP
}

IntraFreqCellInfoSI-List-HCS-ECN0 ::=		SEQUENCE {
	removedIntraFreqCellList			RemovedIntraFreqCellList			OPTIONAL,
	newIntraFreqCellList				NewIntraFreqCellSI-List-HCS-ECN0
}

InterRATCellInfoList ::=			SEQUENCE {
	removedInterRATCellList			RemovedInterRATCellList,
	-- NOTE: Future revisions of dedicated messages including IE newInterRATCellList
	-- should use a corrected version of this IE
	newInterRATCellList				NewInterRATCellList,
	cellsForInterRATMeasList			CellsForInterRATMeasList			OPTIONAL
}

TrafficVolumeMeasurementObjectList ::= SEQUENCE (SIZE (1..maxTrCH)) OF
											UL-TrCH-Identity


TrafficVolumeMeasQuantity ::=		CHOICE {
	rlc-BufferPayload					NULL,
	averageRLC-BufferPayload			TimeInterval,
	varianceOfRLC-BufferPayload			TimeInterval
}

TrafficVolumeReportingQuantity ::= SEQUENCE {
	rlc-RB-BufferPayload				BOOLEAN,
	rlc-RB-BufferPayloadAverage			BOOLEAN,
	rlc-RB-BufferPayloadVariance		BOOLEAN
}

TrafficVolumeReportingCriteria ::= SEQUENCE {
	-- NOTE: transChCriteriaList should be mandatory in later versions of this message
	transChCriteriaList					TransChCriteriaList					OPTIONAL
}

MeasurementValidity ::=				SEQUENCE {
	ue-State							ENUMERATED {
											cell-DCH, all-But-Cell-DCH, all-States }
}

MeasurementReportingMode ::=		SEQUENCE {
	measurementReportTransferMode		TransferMode,
	periodicalOrEventTrigger			PeriodicalOrEventTrigger
}	

TrafficVolumeReportCriteriaSysInfo ::=	CHOICE {
	trafficVolumeReportingCriteria		TrafficVolumeReportingCriteria,
	periodicalReportingCriteria			PeriodicalReportingCriteria
}

UE-InternalMeasQuantity ::=			SEQUENCE {
	measurementQuantity					UE-MeasurementQuantity,
	filterCoefficient					FilterCoefficient					DEFAULT fc0
}

IntraFreqCellInfoSI-List-RSCP-LCR-r4 ::=	SEQUENCE {
	removedIntraFreqCellList			RemovedIntraFreqCellList			OPTIONAL,
	newIntraFreqCellList				NewIntraFreqCellSI-List-RSCP-LCR-r4
}

InterFreqCellInfoSI-List-ECN0-LCR ::=		SEQUENCE {
	removedInterFreqCellList			RemovedInterFreqCellList			OPTIONAL,
	newInterFreqCellList				NewInterFreqCellSI-List-ECN0-LCR-r4		OPTIONAL
}

IntraFreqCellInfoSI-List-HCS-RSCP-LCR-r4 ::=		SEQUENCE {
	removedIntraFreqCellList			RemovedIntraFreqCellList			OPTIONAL,
	newIntraFreqCellList				NewIntraFreqCellSI-List-HCS-RSCP-LCR-r4
}

InterFreqCellInfoSI-List-HCS-ECN0-LCR ::=		SEQUENCE {
	removedInterFreqCellList			RemovedInterFreqCellList			OPTIONAL,
	newInterFreqCellList				NewInterFreqCellSI-List-HCS-ECN0-LCR-r4	OPTIONAL
}

InterFreqCellInfoSI-List-RSCP ::=		SEQUENCE {
	removedInterFreqCellList			RemovedInterFreqCellList			OPTIONAL,
	newInterFreqCellList				NewInterFreqCellSI-List-RSCP		OPTIONAL
}

InterFreqCellInfoSI-List-ECN0 ::=		SEQUENCE {
	removedInterFreqCellList			RemovedInterFreqCellList			OPTIONAL,
	newInterFreqCellList				NewInterFreqCellSI-List-ECN0		OPTIONAL
}

InterFreqCellInfoSI-List-HCS-RSCP ::=		SEQUENCE {
	removedInterFreqCellList			RemovedInterFreqCellList			OPTIONAL,
	newInterFreqCellList				NewInterFreqCellSI-List-HCS-RSCP	OPTIONAL
}

InterFreqCellInfoSI-List-HCS-ECN0 ::=		SEQUENCE {
	removedInterFreqCellList			RemovedInterFreqCellList			OPTIONAL,
	newInterFreqCellList				NewInterFreqCellSI-List-HCS-ECN0	OPTIONAL
}

InterFreqCellInfoSI-List-RSCP-LCR ::=		SEQUENCE {
	removedInterFreqCellList			RemovedInterFreqCellList			OPTIONAL,
	newInterFreqCellList				NewInterFreqCellSI-List-RSCP-LCR-r4		OPTIONAL
}

IntraFreqCellInfoSI-List-ECN0-LCR-r4 ::=		SEQUENCE {
	removedIntraFreqCellList			RemovedIntraFreqCellList			OPTIONAL,
	newIntraFreqCellList				NewIntraFreqCellSI-List-ECN0-LCR-r4
}

InterFreqCellInfoSI-List-HCS-RSCP-LCR ::=		SEQUENCE {
	removedInterFreqCellList			RemovedInterFreqCellList			OPTIONAL,
	newInterFreqCellList				NewInterFreqCellSI-List-HCS-RSCP-LCR-r4	OPTIONAL
}

IntraFreqCellInfoSI-List-HCS-ECN0-LCR-r4 ::=		SEQUENCE {
	removedIntraFreqCellList			RemovedIntraFreqCellList			OPTIONAL,
	newIntraFreqCellList				NewIntraFreqCellSI-List-HCS-ECN0-LCR-r4
}

ReportingInfoForCellDCH-LCR-r4 ::=	SEQUENCE {
	intraFreqReportingQuantity			IntraFreqReportingQuantity,
	measurementReportingMode			MeasurementReportingMode,
	reportCriteria						CellDCH-ReportCriteria-LCR-r4
}

ReportingAmount ::=					ENUMERATED {
										ra1, ra2, ra4, ra8, ra16, ra32,
										ra64, ra-Infinity }

ReportingInterval ::=				ENUMERATED {
										noPeriodicalreporting, ri0-25, 
										ri0-5, ri1, ri2, ri4, ri8, ri16 }

InterFreqRepQuantityRACH-TDD ::=	ENUMERATED {
										timeslotISCP,
										primaryCCPCH-RSCP }

TDD-UL-Interference ::=				INTEGER (-110..-52)

GPS-TOW-Assist ::=					SEQUENCE {
	satID								SatID,
	tlm-Message							BIT STRING (SIZE (14)),
	tlm-Reserved						BIT STRING (SIZE (2)),
	alert								BOOLEAN,
	antiSpoof							BOOLEAN
}

DGPS-CorrectionSatInfo ::=			SEQUENCE {
	satID								SatID,
	iode								IODE,
	udre								UDRE,
	prc									PRC,
	rrc									RRC,
-- dummy1 and dummy2 are not used in this version of the specification and should be ignored.
	dummy1							DeltaPRC,
	dummy2							DeltaRRC,
	-- dummy3 and dummy4 are not used in this version of the specification. They should not
	-- be sent and if received they should be ignored.
	dummy3							DeltaPRC			OPTIONAL,
	dummy4							DeltaRRC			OPTIONAL
}

AlmanacSatInfo ::=					SEQUENCE {
	dataID								INTEGER (0..3),
	satID								SatID,
	e									BIT STRING (SIZE (16)),
	t-oa								BIT STRING (SIZE (8)),
	deltaI								BIT STRING (SIZE (16)),
	omegaDot							BIT STRING (SIZE (16)),
	satHealth							BIT STRING (SIZE (8)),
	a-Sqrt								BIT STRING (SIZE (24)),
	omega0								BIT STRING (SIZE (24)),
	m0									BIT STRING (SIZE (24)),
	omega								BIT STRING (SIZE (24)),
	af0									BIT STRING (SIZE (11)),
	af1									BIT STRING (SIZE (11))
}

PrimaryCPICH-Info ::=				SEQUENCE {
	primaryScramblingCode				PrimaryScramblingCode
}

PrimaryScramblingCode ::=			INTEGER (0..511)

CellAndChannelIdentity ::=			SEQUENCE {
	-- burstType may be set to either value and should be ignored by the receiver for 1.28 Mcps TDD.
	burstType							BurstType,
	midambleShift						MidambleShiftLong,
	timeslot							TimeslotNumber,
	cellParametersID					CellParametersID
}

FrequencyInfo ::=					SEQUENCE {
	modeSpecificInfo					CHOICE {
		fdd									FrequencyInfoFDD,
		tdd									FrequencyInfoTDD	}
}

UE-Positioning-OTDOA-NeighbourCellInfo ::= SEQUENCE {
	modeSpecificInfo	CHOICE	{
		fdd								SEQUENCE {
			primaryCPICH-Info					PrimaryCPICH-Info
		},
		tdd								SEQUENCE{
			cellAndChannelIdentity				CellAndChannelIdentity
		}
	},
	frequencyInfo						FrequencyInfo						OPTIONAL,
	ue-positioning-IPDL-Paremeters					UE-Positioning-IPDL-Parameters					OPTIONAL,
	sfn-SFN-RelTimeDifference			SFN-SFN-RelTimeDifference1,
	sfn-SFN-Drift						SFN-SFN-Drift 						OPTIONAL,
	searchWindowSize					OTDOA-SearchWindowSize,
	positioningMode 	CHOICE{
		ueBased									SEQUENCE {},
		ueAssisted								SEQUENCE {}
	}
}

ReferenceCellPosition ::=			CHOICE {
	ellipsoidPoint						EllipsoidPoint,
	ellipsoidPointWithAltitude			EllipsoidPointAltitude
}

UE-Positioning-IPDL-Parameters ::=				SEQUENCE {
	ip-Spacing							IP-Spacing,
	ip-Length							IP-Length,
	ip-Offset							INTEGER (0..9),
	seed								INTEGER (0..63),
	burstModeParameters					BurstModeParameters 		OPTIONAL
}

Re-EstablishmentTimer ::=			ENUMERATED {
										useT314, useT315
}

SRB-InformationSetupList ::=		SEQUENCE (SIZE (1..maxSRBsetup)) OF
										SRB-InformationSetup

RB-InformationSetupList ::=			SEQUENCE (SIZE (1..maxRBperRAB)) OF
										RB-InformationSetup

UL-CommonTransChInfo ::=			SEQUENCE {
	-- TABULAR: tfc-subset is applicable to FDD only, TDD specifies tfc-subset in individual 
	-- CCTrCH Info.
	tfc-Subset							TFC-Subset							OPTIONAL,
	prach-TFCS							TFCS								OPTIONAL,
	modeSpecificInfo					CHOICE {
		fdd									SEQUENCE {
			ul-TFCS							TFCS
		},
		tdd									SEQUENCE {

			individualUL-CCTrCH-InfoList		IndividualUL-CCTrCH-InfoList
																			OPTIONAL
		}
	}																		OPTIONAL
}

UL-AddReconfTransChInfoList ::=		SEQUENCE (SIZE (1..maxTrCHpreconf)) OF
										UL-AddReconfTransChInformation

DL-CommonTransChInfo ::=			SEQUENCE {
	sccpch-TFCS							TFCS								OPTIONAL,
	-- modeSpecificInfo should be optional. A new version of this IE should be defined 
	-- to be used in later versions of messages using this IE
	modeSpecificInfo					CHOICE {
		fdd									SEQUENCE {
			dl-Parameters						CHOICE {
				dl-DCH-TFCS							TFCS,
				sameAsUL							NULL
			}																OPTIONAL
		},
		tdd									SEQUENCE {
			individualDL-CCTrCH-InfoList		IndividualDL-CCTrCH-InfoList
																			OPTIONAL
		}
	}
}

DL-AddReconfTransChInfoList ::=		SEQUENCE (SIZE (1..maxTrCHpreconf)) OF
										DL-AddReconfTransChInformation

UL-DPCH-InfoPredef ::=				SEQUENCE {
	ul-DPCH-PowerControlInfo			UL-DPCH-PowerControlInfoPredef,
	modeSpecificInfo					CHOICE {
		fdd									SEQUENCE {
			tfci-Existence						BOOLEAN,
			puncturingLimit						PuncturingLimit
		},
		tdd									SEQUENCE {
			commonTimeslotInfo					CommonTimeslotInfo
		}
	}
}

DL-CommonInformationPredef ::=		SEQUENCE {
	dl-DPCH-InfoCommon					DL-DPCH-InfoCommonPredef	OPTIONAL
}

PLMN-Identity ::=					SEQUENCE {
	mcc									MCC,
	mnc									MNC
}

SchedulingInformation ::=			SEQUENCE {
	scheduling							SEQUENCE {
		segCount							SegCount				 		 DEFAULT 1,
		sib-Pos								CHOICE {
			-- The element name indicates the repetition period and the value
			-- (multiplied by two) indicates the position of the first segment.
			rep4								INTEGER (0..1),
			rep8								INTEGER (0..3),
			rep16								INTEGER (0..7),
			rep32								INTEGER (0..15),
			rep64								INTEGER (0..31),
			rep128								INTEGER (0..63),
			rep256								INTEGER (0..127),
			rep512								INTEGER (0..255),
			rep1024								INTEGER (0..511),
			rep2048								INTEGER (0..1023),
			rep4096								INTEGER (0..2047)
		},
		sib-PosOffsetInfo					SibOFF-List						OPTIONAL
	}
}

UE-Positioning-OTDOA-NeighbourCellInfo-UEB ::= SEQUENCE {
	modeSpecificInfo	CHOICE	{
		fdd								SEQUENCE {
			primaryCPICH-Info					PrimaryCPICH-Info
		},
		tdd								SEQUENCE{
			cellAndChannelIdentity				CellAndChannelIdentity
		}
	},
	frequencyInfo						FrequencyInfo						OPTIONAL,
	ue-positioning-IPDL-Paremeters		UE-Positioning-IPDL-Parameters		OPTIONAL,
	sfn-SFN-RelTimeDifference			SFN-SFN-RelTimeDifference1,
	sfn-SFN-Drift						SFN-SFN-Drift						OPTIONAL,
	searchWindowSize					OTDOA-SearchWindowSize,
	relativeNorth						INTEGER (-20000..20000)				OPTIONAL,
	relativeEast						INTEGER (-20000..20000)				OPTIONAL,
	relativeAltitude					INTEGER (-4000..4000)				OPTIONAL,
	fineSFN-SFN							FineSFN-SFN,
	-- actual value roundTripTime = (IE value * 0.0625) + 876
	roundTripTime						INTEGER (0..32766)					OPTIONAL
}

RAT ::=								ENUMERATED {
										utra-FDD,
										utra-TDD,
										gsm,
										cdma2000 }

RAT-Identifier ::=					ENUMERATED {
										gsm, cdma2000 }

TFCS-IdentityPlain ::=				INTEGER (1..8)

CommonTimeslotInfo ::=				SEQUENCE {
	-- TABULAR: secondInterleavingMode is MD, but since it can be encoded in a single
	-- bit it is not defined as OPTIONAL.
	secondInterleavingMode				SecondInterleavingMode,
	tfci-Coding							TFCI-Coding							OPTIONAL,
	puncturingLimit						PuncturingLimit,
	repetitionPeriodAndLength			RepetitionPeriodAndLength			OPTIONAL
}

UplinkTimeslotsCodes ::=			SEQUENCE {
	dynamicSFusage						BOOLEAN,
	firstIndividualTimeslotInfo			IndividualTimeslotInfo,
	ul-TS-ChannelisationCodeList		UL-TS-ChannelisationCodeList,
	moreTimeslots						CHOICE {
		noMore								NULL,
		additionalTimeslots					CHOICE {
			consecutive							SEQUENCE {
				numAdditionalTimeslots				INTEGER (1..maxTS-1)
			},
			timeslotList						SEQUENCE (SIZE (1..maxTS-1)) OF
													UplinkAdditionalTimeslots
		}
	}
}

AvailableSignatures ::=			BIT STRING {
									signature15(0),
									signature14(1),
									signature13(2),
									signature12(3),
									signature11(4),
									signature10(5),
									signature9(6),
									signature8(7),
									signature7(8),
									signature6(9),
									signature5(10),
									signature4(11),
									signature3(12),
									signature2(13),
									signature1(14),
									signature0(15)
									}	 (SIZE(16))

SF-PRACH ::=						ENUMERATED {
										sfpr32, sfpr64, sfpr128, sfpr256 }

PreambleScramblingCodeWordNumber ::=	INTEGER (0..15)	

PuncturingLimit ::=					ENUMERATED {
										pl0-40, pl0-44, pl0-48, pl0-52, pl0-56,
										pl0-60, pl0-64, pl0-68, pl0-72, pl0-76,
										pl0-80, pl0-84, pl0-88, pl0-92, pl0-96, pl1 }

AvailableSubChannelNumbers ::=		BIT STRING {
										subCh11(0),
										subCh10(1),
									 	subCh9(2),
									 	subCh8(3),
									 	subCh7(4),
									 	subCh6(5),
									 	subCh5(6),
									 	subCh4(7),
									 	subCh3(8),
									 	subCh2(9),
									 	subCh1(10),
									 	subCh0(11)
										} 	 (SIZE(12))										

T-CRMaxHyst ::=						ENUMERATED {
										notUsed, t10, t20, t30,
										t40, t50, t60, t70 }

PRACH-Midamble ::=					ENUMERATED {
										direct,
										direct-Inverted }

ASCSetting-FDD ::=						SEQUENCE {
	-- TABULAR: accessServiceClass-FDD is MD in tabular description
	-- Default value is previous ASC
	-- If this is the first ASC, the default value is all available signature and sub-channels
	accessServiceClass-FDD					AccessServiceClass-FDD	OPTIONAL
}			

ASCSetting-TDD ::=						SEQUENCE {
	-- TABULAR: accessServiceClass-TDD is MD in tabular description
	-- Default value is previous ASC
	-- If this is the first ASC, the default value is all available channelisation codes and
	-- all available sub-channels with subchannelSize=size1.
	accessServiceClass-TDD					AccessServiceClass-TDD	OPTIONAL
}

PersistenceScalingFactor ::=		ENUMERATED {
										psf0-9, psf0-8, psf0-7, psf0-6,
										psf0-5, psf0-4, psf0-3, psf0-2 }

AC-To-ASC-Mapping ::=				INTEGER (0..7)		

PowerRampStep ::=					INTEGER (1..8)

PreambleRetransMax ::=				INTEGER (1..64)

NB01 ::=							INTEGER (0..50)

AICH-TransmissionTiming ::=			ENUMERATED {
										e0, e1 }

TDD-PRACH-CCodeList ::= 			CHOICE {
	sf8									SEQUENCE (SIZE (1..8)) OF 
											TDD-PRACH-CCode8,
-- Channelisation codes cc16-9, cc16-10, cc16-11, cc16-12, cc16-13, cc16-14,
-- cc16-15 and cc16-16 shall not be used
	sf16								SEQUENCE (SIZE (1..8)) OF
											TDD-PRACH-CCode16
}

TDD768-PRACH-CCodeList ::= 			CHOICE {
	sf32								SEQUENCE (SIZE (1..16)) OF 
											TDD768-PRACH-CCode32,
-- Channelisation codes cc32-17, cc32-18, cc32-19, cc32-20, cc32-21, cc32-22,
-- cc32-23, cc32-24, cc32-25, cc32-26, cc32-27, cc32-28, cc32-29, cc32-30, cc32-31
-- and cc32-32 shall not be used
	sf16								SEQUENCE (SIZE (1..16)) OF
											TDD768-PRACH-CCode16,
	sf8									SEQUENCE (SIZE (1..8)) OF
											TDD768-PRACH-CCode8
}


MasterInformationBlock ::=			SEQUENCE {
		mib-ValueTag					MIB-ValueTag,
		-- TABULAR: The PLMN identity and ANSI-41 core network information
		-- are included in PLMN-Type.
		plmn-Type						PLMN-Type,
		sibSb-ReferenceList				SIBSb-ReferenceList,
	-- Extension mechanism for non- release99 information
		v690NonCriticalExtensions			SEQUENCE {
			masterInformationBlock-v690ext		MasterInformationBlock-v690ext,
			nonCriticalExtensions				SEQUENCE {}							OPTIONAL
		}	OPTIONAL
}


PLMN-Type ::=						CHOICE {
	gsm-MAP								SEQUENCE {
		plmn-Identity						PLMN-Identity
	},
	ansi-41							SEQUENCE {
		p-REV							P-REV,
		min-P-REV						Min-P-REV,
		sid								SID,
		nid								NID
	},
	gsm-MAP-and-ANSI-41				SEQUENCE {
		plmn-Identity					PLMN-Identity,
		p-REV							P-REV,
		min-P-REV						Min-P-REV,
		sid								SID,
		nid								NID
	},
	spare							NULL
}

SIBSb-ReferenceList ::=				SEQUENCE (SIZE (1..maxSIB)) OF
										SchedulingInformationSIBSb

MasterInformationBlock-v690ext ::=	SEQUENCE {
	multiplePLMN-List					MultiplePLMN-List-r6			OPTIONAL
}

Min-P-REV ::=							BIT STRING (SIZE (8))

ASCSetting-TDD-r7 ::=						SEQUENCE {
	-- TABULAR: accessServiceClass-TDD is MD in tabular description
	-- Default value is previous ASC
	-- If this is the first ASC, the default value is all available channelisation codes and
	-- all available sub-channels with subchannelSize=size1.
	accessServiceClass-TDD						AccessServiceClass-TDD-r7	OPTIONAL
}

NID ::=									BIT STRING (SIZE (16))

P-REV ::=								BIT STRING (SIZE (8))

SID ::=									BIT STRING (SIZE (15))

SchedulingInformationSIBSb ::=			SEQUENCE {
	sibSb-Type							SIBSb-TypeAndTag,
	scheduling							SchedulingInformation
}


PLMN-IdentityWithOptionalMCC-r6 ::=	SEQUENCE {
	mcc									MCC						OPTIONAL,
	mnc									MNC
}

MultiplePLMN-List-r6 ::=			SEQUENCE {
	mibPLMN-Identity					BOOLEAN,
	multiplePLMNs						SEQUENCE (SIZE (1..5)) OF
											PLMN-IdentityWithOptionalMCC-r6
}

SYNC-UL-Info-r4 ::=					SEQUENCE {
	sync-UL-Codes-Bitmap				BIT STRING {
											code7(0),
											code6(1),
											code5(2),
											code4(3),
											code3(4),
											code2(5),
											code1(6),
											code0(7)
											} ( SIZE (8)),
	-- Actual value prxUpPCHdes = IE value - 120
	prxUpPCHdes							INTEGER (0..62),
	powerRampStep						INTEGER (0..3),
	max-SYNC-UL-Transmissions			ENUMERATED { tr1, tr2, tr4, tr8 } ,
    mmax                                INTEGER(1..32)
}

PRACH-Definition-LCR-r4 ::=			SEQUENCE {
	timeslot							TimeslotNumber-PRACH-LCR-r4,
	prach-ChanCodes-LCR					PRACH-ChanCodes-LCR-r4,
	midambleShiftAndBurstType			MidambleShiftAndBurstType-LCR-r4,
	fpach-Info							FPACH-Info-r4
}

CommonTransChTFS-LCR ::=				SEQUENCE {
	tti									CHOICE {
		tti5								CommonDynamicTF-InfoList,
		tti10								CommonDynamicTF-InfoList,
		tti20								CommonDynamicTF-InfoList,
		tti40								CommonDynamicTF-InfoList,
		tti80								CommonDynamicTF-InfoList,
		dynamic								CommonDynamicTF-InfoList-DynamicTTI
	},
	semistaticTF-Information			SemistaticTF-Information
}

ASCSetting-TDD-LCR-r4 ::=						SEQUENCE {
	-- TABULAR: accessServiceClass-TDD-LCR is MD in tabular description
	-- Default value is previous ASC
	-- If this is the first ASC, the default value is all available SYNC_UL codes and
	-- all available sub-channels with subchannelSize=size1. 
	accessServiceClass-TDD-LCR					AccessServiceClass-TDD-LCR-r4  	OPTIONAL
}

PCPICH-UsageForChannelEst ::=		ENUMERATED {
										mayBeUsed,
										shallNotBeUsed }

SecondaryCPICH-Info ::=				SEQUENCE {
	secondaryDL-ScramblingCode			SecondaryScramblingCode				OPTIONAL,
	channelisationCode					ChannelisationCode256
}	

PositionFixedOrFlexible ::=			ENUMERATED {
										fixed,
										flexible }

CommonTimeslotInfoSCCPCH ::=		SEQUENCE {
	-- TABULAR: secondInterleavingMode is MD, but since it can be encoded in a single
	-- bit it is not defined as OPTIONAL.
	secondInterleavingMode				SecondInterleavingMode,
	tfci-Coding							TFCI-Coding							OPTIONAL,
	puncturingLimit						PuncturingLimit,
	repetitionPeriodLengthAndOffset		RepetitionPeriodLengthAndOffset		OPTIONAL
}	

IndividualTimeslotInfo ::=			SEQUENCE {
	timeslotNumber						TimeslotNumber,
	tfci-Existence						BOOLEAN,
	midambleShiftAndBurstType			MidambleShiftAndBurstType
}

SCCPCH-ChannelisationCodeList ::=	SEQUENCE (SIZE (1..16)) OF
										SCCPCH-ChannelisationCode

FACH-PCH-Information ::=			SEQUENCE {
	transportFormatSet					TransportFormatSet,
	transportChannelIdentity			TransportChannelIdentity,
	ctch-Indicator						BOOLEAN
}

ChannelisationCode256 ::=			INTEGER (0..255)

PI-CountPerFrame ::=				ENUMERATED {
										e18, e36, e72, e144 }

TDD-PICH-CCode ::=					ENUMERATED {
										cc16-1, cc16-2, cc16-3, cc16-4,
										cc16-5, cc16-6, cc16-7, cc16-8,
										cc16-9, cc16-10, cc16-11, cc16-12,
										cc16-13, cc16-14, cc16-15, cc16-16 }

MidambleShiftAndBurstType ::=		SEQUENCE {
	burstType							CHOICE {	
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2,
			midambleAllocationMode				CHOICE {
				defaultMidamble						NULL,
				commonMidamble						NULL,
				ueSpecificMidamble					SEQUENCE {
					midambleShift						MidambleShiftShort
				}
			}
		},
		type3								SEQUENCE {
			midambleConfigurationBurstType1and3	MidambleConfigurationBurstType1and3,
			midambleAllocationMode				CHOICE {
				defaultMidamble						NULL,
				ueSpecificMidamble					SEQUENCE {
					midambleShift						MidambleShiftLong
				}
			}
		}
	}
}

PagingIndicatorLength ::=			ENUMERATED {
										pi4, pi8, pi16 }

N-GAP ::=							ENUMERATED {
										f2, f4, f8 }

N-PCH ::=							INTEGER (1..8)		

IndividualTimeslotInfo-LCR-r4-ext ::=		SEQUENCE {
-- timeslotNumber and tfci-Existence is taken from IndividualTimeslotInfo.
-- midambleShiftAndBurstType in IndividualTimeslotInfo shall be ignored.
	midambleShiftAndBurstType			MidambleShiftAndBurstType-LCR-r4,
	modulation							ENUMERATED { mod-QPSK, mod-8PSK },
	ss-TPC-Symbols						ENUMERATED { zero, one, sixteenOverSF }
}

TimeslotNumber-LCR-r4 ::=				INTEGER (0..6)

PichChannelisationCodeList-LCR-r4 ::=	SEQUENCE (SIZE (1..2)) OF
											DL-TS-ChannelisationCode

			MidambleShiftAndBurstType-LCR-r4 ::=	SEQUENCE {
	midambleAllocationMode				CHOICE {
		defaultMidamble						NULL,
		commonMidamble						NULL,
		ueSpecificMidamble					SEQUENCE {
			midambleShift						INTEGER (0..15)
		}
	},
	-- Actual value midambleConfiguration = IE value * 2
	midambleConfiguration				INTEGER (1..8)
}	

RepPerLengthOffset-PICH ::=			CHOICE {
	rpp4-2								INTEGER (0..3), 
	rpp8-2								INTEGER (0..7), 
	rpp8-4								INTEGER (0..7),
	rpp16-2								INTEGER (0..15), 
	rpp16-4								INTEGER (0..15), 
	rpp32-2								INTEGER (0..31), 
	rpp32-4								INTEGER (0..31), 
	rpp64-2								INTEGER (0..63), 
	rpp64-4								INTEGER (0..63)
}

TimerOSD-r6 ::=						ENUMERATED {
										ms40, ms80, ms120, ms160, ms240, ms320, ms480, ms640,
										ms960, ms1280, ms1920, ms2560, ms3840, ms5120 }					

WindowSizeOSD-r6 ::=				ENUMERATED {
										ws8, ws16, ws32, ws40, ws48,
										ws56, ws64 }

DL-TS-ChannelisationCodesShort ::=	SEQUENCE {
	codesRepresentation					CHOICE {
		consecutive							SEQUENCE {
			firstChannelisationCode				DL-TS-ChannelisationCode,
			lastChannelisationCode				DL-TS-ChannelisationCode
		},
		bitmap								BIT STRING {
												chCode16-SF16(0),
												chCode15-SF16(1),
												chCode14-SF16(2),
												chCode13-SF16(3),
												chCode12-SF16(4),
												chCode11-SF16(5),
												chCode10-SF16(6),
												chCode9-SF16(7),
												chCode8-SF16(8),
												chCode7-SF16(9),
												chCode6-SF16(10),
												chCode5-SF16(11),
												chCode4-SF16(12),
												chCode3-SF16(13),
												chCode2-SF16(14),
												chCode1-SF16(15)
												} 	(SIZE (16))
	}
}

DownlinkAdditionalTimeslots ::=		SEQUENCE {
	parameters							CHOICE {
		sameAsLast							SEQUENCE {
			timeslotNumber						TimeslotNumber
		},
		newParameters						SEQUENCE {
			individualTimeslotInfo				IndividualTimeslotInfo,
			dl-TS-ChannelisationCodesShort		DL-TS-ChannelisationCodesShort
		}
	}
}

IndividualTimeslotInfo-LCR-r4 ::=	SEQUENCE {
	timeslotNumber						TimeslotNumber-LCR-r4,
	tfci-Existence						BOOLEAN,
	midambleShiftAndBurstType			MidambleShiftAndBurstType-LCR-r4,
	modulation							ENUMERATED { mod-QPSK, mod-8PSK },
	ss-TPC-Symbols						ENUMERATED { zero, one, sixteenOverSF },
	additionalSS-TPC-Symbols			INTEGER(1..15)		OPTIONAL
}

DownlinkAdditionalTimeslots-LCR-r4 ::=	SEQUENCE {
	parameters							CHOICE {
		sameAsLast							SEQUENCE {
			timeslotNumber						TimeslotNumber-LCR-r4
		},
		newParameters						SEQUENCE {
			individualTimeslotInfo				IndividualTimeslotInfo-LCR-r4,
			dl-TS-ChannelisationCodesShort		DL-TS-ChannelisationCodesShort
		}
	}
}

TFCS-ReconfAdd ::=					SEQUENCE{
	ctfcSize							CHOICE{
		ctfc2Bit							SEQUENCE (SIZE (1..maxTFC)) OF SEQUENCE {
			ctfc2								INTEGER (0..3),
			powerOffsetInformation				PowerOffsetInformation			OPTIONAL
		},
		ctfc4Bit							SEQUENCE (SIZE (1..maxTFC)) OF SEQUENCE {
			ctfc4 								INTEGER (0..15),
			powerOffsetInformation				PowerOffsetInformation			OPTIONAL
		},
		ctfc6Bit							SEQUENCE (SIZE (1..maxTFC)) OF SEQUENCE {
			ctfc6								INTEGER (0..63),
			powerOffsetInformation				PowerOffsetInformation			OPTIONAL
		},
		ctfc8Bit							SEQUENCE (SIZE (1..maxTFC)) OF SEQUENCE {
			ctfc8								INTEGER (0..255),
			powerOffsetInformation				PowerOffsetInformation			OPTIONAL
		},
		ctfc12Bit							SEQUENCE (SIZE(1..maxTFC)) OF SEQUENCE {
			ctfc12								INTEGER (0..4095),
 			powerOffsetInformation				PowerOffsetInformation			OPTIONAL
		},
		ctfc16Bit							SEQUENCE (SIZE (1..maxTFC)) OF SEQUENCE {
			ctfc16								INTEGER(0..65535),
			powerOffsetInformation				PowerOffsetInformation			OPTIONAL
		},
		ctfc24Bit							SEQUENCE (SIZE (1..maxTFC)) OF SEQUENCE {
			ctfc24								INTEGER(0..16777215),
			powerOffsetInformation				PowerOffsetInformation			OPTIONAL
		}
	}
}

TFCS-Removal ::=					SEQUENCE {
	tfci								INTEGER (0..1023)
}

TFCS-RemovalList ::=				SEQUENCE (SIZE (1..maxTFC)) OF
										TFCS-Removal

SplitType ::=						ENUMERATED {
										hardSplit, logicalSplit }

TFCI-Field2-Information ::=			CHOICE {
	tfci-Range							TFCI-RangeList,
	explicit-config						ExplicitTFCS-Configuration
}

DedicatedDynamicTF-InfoList ::=		SEQUENCE (SIZE (1..maxTF)) OF
										DedicatedDynamicTF-Info

CommonDynamicTF-InfoList ::=		SEQUENCE (SIZE (1..maxTF)) OF
										CommonDynamicTF-Info

SemistaticTF-Information ::=		SEQUENCE {
	-- TABULAR: Transmission time interval has been included in the IE CommonTransChTFS.
	channelCodingType					ChannelCodingType,
	rateMatchingAttribute				RateMatchingAttribute,
	crc-Size							CRC-Size
}

GainFactorInformation ::=			CHOICE {
	signalledGainFactors				SignalledGainFactors,
	computedGainFactors					ReferenceTFC-ID
}

PowerOffsetPp-m ::=					INTEGER (-5..10)

OctetModeRLC-SizeInfoType2 ::=		CHOICE {
	-- Actual size = (sizeType1 * 8) + 48
	sizeType1							INTEGER (0..31),
	-- Actual size = (sizeType2 * 16) + 312
	sizeType2							INTEGER (0..63),
	-- Actual size = (sizeType3 *64) + 1384
	sizeType3							INTEGER (0..56)
}

UplinkTimeslotsCodes-VHCR ::=		SEQUENCE {
	dynamicSFusage						BOOLEAN,
	firstIndividualTimeslotInfo			IndividualTimeslotInfo-VHCR,
	ul-TS-ChannelisationCodeList		UL-TS-ChannelisationCodeList-VHCR,
	moreTimeslots						CHOICE {
		noMore								NULL,
		additionalTimeslots					CHOICE {
			consecutive							SEQUENCE {
				numAdditionalTimeslots				INTEGER (1..maxTS-1)
			},
			timeslotList						SEQUENCE (SIZE (1..maxTS-1)) OF
													UplinkAdditionalTimeslots
		}
	}
}

UplinkTimeslotsCodes-LCR-r4 ::=		SEQUENCE {
	dynamicSFusage						BOOLEAN,
	firstIndividualTimeslotInfo			IndividualTimeslotInfo-LCR-r4,
	ul-TS-ChannelisationCodeList		UL-TS-ChannelisationCodeList,
	moreTimeslots						CHOICE {
		noMore								NULL,
		additionalTimeslots					CHOICE {
			consecutive							SEQUENCE {
				numAdditionalTimeslots				INTEGER (1..maxTS-LCR-1)
			},
			timeslotList						SEQUENCE (SIZE (1..maxTS-LCR-1)) OF
													UplinkAdditionalTimeslots-LCR-r4
		}
	}
}

IndividualTimeslotInfo-VHCR ::=			SEQUENCE {
	timeslotNumber						TimeslotNumber,
	tfci-Existence						BOOLEAN,
	midambleShiftAndBurstType-VHCR		MidambleShiftAndBurstType-VHCR
}

DownlinkAdditionalTimeslots-VHCR ::= SEQUENCE {
	parameters							CHOICE {
		sameAsLast							SEQUENCE {
			timeslotNumber						TimeslotNumber
		},
		newParameters						SEQUENCE {
			individualTimeslotInfo				IndividualTimeslotInfo-VHCR,
			dl-TS-ChannelisationCodesShort		DL-TS-ChannelisationCodesShort-VHCR
		}
	}
}

DedicatedDynamicTF-InfoList-DynamicTTI ::= SEQUENCE (SIZE (1..maxTF)) OF
										DedicatedDynamicTF-Info-DynamicTTI

CommonDynamicTF-InfoList-DynamicTTI ::= SEQUENCE (SIZE (1..maxTF)) OF
										CommonDynamicTF-Info-DynamicTTI

SCCPCH-ChannelisationCodeList-VHCR ::= SEQUENCE (SIZE (1..32)) OF
										SCCPCH-ChannelisationCode-VHCR

TDD768-PICH-CCode ::=				ENUMERATED {
										cc32-1, cc32-2, cc32-3, cc32-4,
										cc32-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

AvailableMinimumSF-ListVCAM ::=		SEQUENCE (SIZE (1..maxPCPCH-SF)) OF
										AvailableMinimumSF-VCAM

PCPCH-ChannelInfo ::=				SEQUENCE {
	pcpch-UL-ScramblingCode				INTEGER (0..79),
	pcpch-DL-ChannelisationCode			INTEGER (0..511),
	pcpch-DL-ScramblingCode				SecondaryScramblingCode				OPTIONAL,
	pcp-Length							PCP-Length,
	ucsm-Info							UCSM-Info							OPTIONAL
}

NewIntraFreqCellSI-List-RSCP ::=		SEQUENCE (SIZE (1..maxCellMeas)) OF
											NewIntraFreqCellSI-RSCP

FilterCoefficient ::=				ENUMERATED {
										fc0, fc1, fc2, fc3, fc4, fc5, 
										fc6, fc7, fc8, fc9, fc11, fc13, 
										fc15, fc17, fc19, spare1 }

IntraFreqMeasQuantity-FDD ::=		ENUMERATED {
										cpich-Ec-N0,
										cpich-RSCP,
										pathloss,
										dummy }			

IntraFreqMeasQuantity-TDDList ::=	SEQUENCE (SIZE (1..4)) OF
										IntraFreqMeasQuantity-TDD																	

SFN-SFN-OTD-Type ::=				ENUMERATED {
										noReport,
										type1,
										type2 }

IntraFreqRepQuantityRACH-FDD ::=	ENUMERATED {
										cpich-EcN0, cpich-RSCP, 
										pathloss, noReport }

IntraFreqRepQuantityRACH-TDD ::=	ENUMERATED {
										timeslotISCP,
										primaryCCPCH-RSCP,
										noReport }

IntraFreqRepQuantityRACH-TDDList ::= SEQUENCE (SIZE (1..2)) OF
										IntraFreqRepQuantityRACH-TDD										

IntraFreqReportingQuantity ::=		SEQUENCE {
	activeSetReportingQuantities		CellReportingQuantities,
	monitoredSetReportingQuantities		CellReportingQuantities,
	detectedSetReportingQuantities		CellReportingQuantities				OPTIONAL
}

CellDCH-ReportCriteria ::=			CHOICE {
	intraFreqReportingCriteria			IntraFreqReportingCriteria,
	periodicalReportingCriteria			PeriodicalReportingCriteria
}

RemovedIntraFreqCellList ::=		CHOICE {
	removeAllIntraFreqCells				NULL,
	removeSomeIntraFreqCells			SEQUENCE (SIZE (1..maxCellMeas)) OF
											IntraFreqCellID,
	removeNoIntraFreqCells				NULL
}

NewIntraFreqCellSI-List-ECN0 ::=		SEQUENCE (SIZE (1..maxCellMeas)) OF
										NewIntraFreqCellSI-ECN0

RemovedInterRATCellList ::=		CHOICE {
	removeAllInterRATCells			NULL,
	removeSomeInterRATCells			SEQUENCE (SIZE (1..maxCellMeas)) OF
											InterRATCellID,
	removeNoInterRATCells			NULL
}

NewInterRATCellList-B ::=			SEQUENCE (SIZE (1..maxCellMeas)) OF
										NewInterRATCell-B

NewIntraFreqCellSI-List-HCS-RSCP ::=	SEQUENCE (SIZE (1..maxCellMeas)) OF
										NewIntraFreqCellSI-HCS-RSCP

NewIntraFreqCellSI-List-HCS-ECN0 ::=	SEQUENCE (SIZE (1..maxCellMeas)) OF
										NewIntraFreqCellSI-HCS-ECN0

NewInterRATCellList ::=			SEQUENCE (SIZE (1..maxCellMeas)) OF
										NewInterRATCell

CellsForInterRATMeasList ::=			SEQUENCE (SIZE  (1..maxCellMeas)) OF
										InterRATCellID										

UL-TrCH-Identity ::=					CHOICE{
	dch									TransportChannelIdentity,
	-- Note: the reference to CPCH in the element name below is incorrect. The name is not changed
	-- to keep it aligned with R99.
	rachorcpch							NULL,
	usch								TransportChannelIdentity
}

TimeInterval ::=					INTEGER (1..13)

TransChCriteriaList ::=			SEQUENCE (SIZE (1..maxTrCH)) OF
										TransChCriteria

TransferMode ::=					ENUMERATED {
										acknowledgedModeRLC,
										unacknowledgedModeRLC }										

PeriodicalOrEventTrigger ::=		ENUMERATED {
										periodical,
										eventTrigger }

PeriodicalReportingCriteria ::=		SEQUENCE {
	reportingAmount						ReportingAmount					DEFAULT ra-Infinity,
	reportingInterval					ReportingIntervalLong
}

UE-MeasurementQuantity ::=			ENUMERATED {
										ue-TransmittedPower,
										utra-Carrier-RSSI,
										ue-RX-TX-TimeDifference }

NewIntraFreqCellSI-List-RSCP-LCR-r4 ::=		SEQUENCE (SIZE (1..maxCellMeas)) OF
											NewIntraFreqCellSI-RSCP-LCR-r4

CellDCH-ReportCriteria-LCR-r4 ::=	CHOICE {
	intraFreqReportingCriteria			IntraFreqReportingCriteria-LCR-r4,
	periodicalReportingCriteria			PeriodicalReportingCriteria
}


RemovedInterFreqCellList ::=		CHOICE {
	removeAllInterFreqCells				NULL,
	removeSomeInterFreqCells			SEQUENCE (SIZE (1..maxCellMeas)) OF
											InterFreqCellID,
	removeNoInterFreqCells				NULL
}

NewInterFreqCellSI-List-ECN0-LCR-r4 ::=		SEQUENCE (SIZE (1..maxCellMeas)) OF
										NewInterFreqCellSI-ECN0-LCR-r4

NewIntraFreqCellSI-List-HCS-RSCP-LCR-r4 ::=	SEQUENCE (SIZE (1..maxCellMeas)) OF
										NewIntraFreqCellSI-HCS-RSCP-LCR-r4										

NewInterFreqCellSI-List-RSCP ::=		SEQUENCE (SIZE (1..maxCellMeas)) OF
										NewInterFreqCellSI-RSCP

NewInterFreqCellSI-List-ECN0 ::=			SEQUENCE (SIZE (1..maxCellMeas)) OF
										NewInterFreqCellSI-ECN0
										
NewInterFreqCellSI-List-HCS-RSCP ::=			SEQUENCE (SIZE (1..maxCellMeas)) OF
										NewInterFreqCellSI-HCS-RSCP

NewInterFreqCellSI-List-HCS-ECN0 ::=			SEQUENCE (SIZE (1..maxCellMeas)) OF
										NewInterFreqCellSI-HCS-ECN0

NewInterFreqCellSI-List-RSCP-LCR-r4 ::=		SEQUENCE (SIZE (1..maxCellMeas)) OF
										NewInterFreqCellSI-RSCP-LCR-r4

NewInterFreqCellSI-List-HCS-ECN0-LCR-r4 ::=	SEQUENCE (SIZE (1..maxCellMeas)) OF
										NewInterFreqCellSI-HCS-ECN0-LCR-r4

NewInterFreqCellSI-List-HCS-RSCP-LCR-r4 ::=	SEQUENCE (SIZE (1..maxCellMeas)) OF
										NewInterFreqCellSI-HCS-RSCP-LCR-r4

NewIntraFreqCellSI-List-HCS-ECN0-LCR-r4 ::=	SEQUENCE (SIZE (1..maxCellMeas)) OF
										NewIntraFreqCellSI-HCS-ECN0-LCR-r4
										
IODE ::=							INTEGER (0..255)

UDRE ::=							ENUMERATED {
										lessThan1,
										between1-and-4,
										between4-and-8,
										over8 }

PRC ::=								INTEGER (-2047..2047)

RRC ::=								INTEGER (-127..127)

DeltaPRC ::=						INTEGER (-127..127)

DeltaRRC ::=						INTEGER (-7..7)

BurstType ::=						ENUMERATED {
										type1, type2 }

MidambleShiftLong ::=				INTEGER (0..15)

FrequencyInfoFDD ::=				SEQUENCE {
	uarfcn-UL							UARFCN				OPTIONAL,
	uarfcn-DL							UARFCN
}

IP-Spacing ::=						ENUMERATED {
										e5, e7, e10, e15, e20,
										e30, e40, e50 }

IP-Length ::=						ENUMERATED {
										ipl5, ipl10 }

SFN-SFN-RelTimeDifference1 ::=		SEQUENCE {
	sfn-Offset							INTEGER (0 .. 4095),
	sfn-sfn-Reltimedifference			INTEGER (0.. 38399)
}					

SFN-SFN-Drift ::= 					ENUMERATED {
										sfnsfndrift0, sfnsfndrift1, sfnsfndrift2,
										sfnsfndrift3, sfnsfndrift4, sfnsfndrift5,
										sfnsfndrift8, sfnsfndrift10, sfnsfndrift15,
										sfnsfndrift25, sfnsfndrift35, sfnsfndrift50,
										sfnsfndrift65, sfnsfndrift80, sfnsfndrift100,
										sfnsfndrift-1, sfnsfndrift-2, sfnsfndrift-3,
										sfnsfndrift-4, sfnsfndrift-5, sfnsfndrift-8,
										sfnsfndrift-10, sfnsfndrift-15, sfnsfndrift-25,
										sfnsfndrift-35, sfnsfndrift-50, sfnsfndrift-65,
										sfnsfndrift-80, sfnsfndrift-100}

OTDOA-SearchWindowSize ::=			ENUMERATED {
										c20, c40, c80, c160, c320,
										c640, c1280, moreThan1280 }

EllipsoidPoint ::=					SEQUENCE {	
	latitudeSign		ENUMERATED { north, south },
	latitude			INTEGER (0..8388607),
	longitude			INTEGER (-8388608..8388607)
}

EllipsoidPointAltitude ::=			SEQUENCE {
	latitudeSign		ENUMERATED { north, south },
	latitude			INTEGER (0..8388607),
	longitude			INTEGER (-8388608..8388607),
	altitudeDirection	ENUMERATED {height, depth},
	altitude			INTEGER (0..32767)
}

SRB-InformationSetup ::=			SEQUENCE {
	-- The default value for rb-Identity is the smallest value not used yet.
	rb-Identity							RB-Identity							OPTIONAL,
	rlc-InfoChoice						RLC-InfoChoice,
	rb-MappingInfo						RB-MappingInfo
}

RB-InformationSetup ::=				SEQUENCE {
	rb-Identity							RB-Identity,
	pdcp-Info							PDCP-Info							OPTIONAL,
	rlc-InfoChoice						RLC-InfoChoice,
	rb-MappingInfo						RB-MappingInfo
}

TFC-Subset ::=						CHOICE {
	minimumAllowedTFC-Number			TFC-Value,
	allowedTFC-List						AllowedTFC-List,
	non-allowedTFC-List					Non-allowedTFC-List,
	restrictedTrChInfoList				RestrictedTrChInfoList,
	fullTFCS							NULL
}

IndividualUL-CCTrCH-InfoList ::=	SEQUENCE (SIZE (1..maxCCTrCH)) OF
										IndividualUL-CCTrCH-Info

UL-AddReconfTransChInformation ::= SEQUENCE {
	ul-TransportChannelType				UL-TrCH-Type,
	transportChannelIdentity			TransportChannelIdentity,
	transportFormatSet					TransportFormatSet
}

IndividualDL-CCTrCH-InfoList ::=	SEQUENCE (SIZE (1..maxCCTrCH)) OF
										IndividualDL-CCTrCH-Info

DL-AddReconfTransChInformation ::= 	SEQUENCE {
	dl-TransportChannelType				DL-TrCH-Type,
	dl-transportChannelIdentity			TransportChannelIdentity,
	tfs-SignallingMode					CHOICE {
		explicit-config						TransportFormatSet,
		sameAsULTrCH						UL-TransportChannelIdentity
	},
	dch-QualityTarget					QualityTarget						OPTIONAL,
	-- dummy is not used in this version of the specification, it should 
	-- not be sent and if received it should be ignored.
	dummy								TM-SignallingInfo					OPTIONAL
}

UL-DPCH-PowerControlInfoPredef ::=		CHOICE {
	fdd									SEQUENCE {
		-- TABULAR: TPC step size nested inside PowerControlAlgorithm
		powerControlAlgorithm				PowerControlAlgorithm
	},
	tdd									SEQUENCE {
		-- dpch-ConstantValue shall be ignored if in 1.28Mcps TDD mode.
		dpch-ConstantValue					ConstantValueTdd
	}
}

DL-DPCH-InfoCommonPredef ::=		SEQUENCE {
	modeSpecificInfo					CHOICE {
		fdd									SEQUENCE {
			-- TABULAR: The number of pilot bits is nested inside the spreading factor.
			spreadingFactorAndPilot				SF512-AndPilot,
			positionFixedOrFlexible				PositionFixedOrFlexible,
			tfci-Existence						BOOLEAN
		},
		tdd									SEQUENCE {
			commonTimeslotInfo					CommonTimeslotInfo
		}
	}
}

MCC ::=								SEQUENCE (SIZE (3)) OF
										Digit

MNC ::=								SEQUENCE (SIZE (2..3)) OF
										Digit

SecondInterleavingMode ::=			ENUMERATED {
										frameRelated, timeslotRelated }

TFCI-Coding ::=						ENUMERATED { 
										tfci-bits-4, tfci-bits-8,
										tfci-bits-16, tfci-bits-32 }

RepetitionPeriodAndLength ::=		CHOICE {
	repetitionPeriod1					NULL,
	-- repetitionPeriod2 could just as well be NULL also.
	repetitionPeriod2					INTEGER (1..1),
	repetitionPeriod4					INTEGER (1..3),
	repetitionPeriod8					INTEGER (1..7),
	repetitionPeriod16					INTEGER (1..15),
	repetitionPeriod32					INTEGER (1..31),
	repetitionPeriod64					INTEGER (1..63)
}

UL-TS-ChannelisationCodeList ::= 	SEQUENCE (SIZE (1..2)) OF
										UL-TS-ChannelisationCode

UplinkAdditionalTimeslots ::=		SEQUENCE {
	parameters							CHOICE {
		sameAsLast							SEQUENCE {
			timeslotNumber						TimeslotNumber
		},
		newParameters						SEQUENCE {
			individualTimeslotInfo						IndividualTimeslotInfo,
			ul-TS-ChannelisationCodeList				UL-TS-ChannelisationCodeList
		}
	}
}

TDD-PRACH-CCode8 ::=				ENUMERATED {
										cc8-1, cc8-2, cc8-3, cc8-4,
										cc8-5, cc8-6, cc8-7, cc8-8 }

TDD-PRACH-CCode16 ::=				ENUMERATED {
										cc16-1, cc16-2, cc16-3, cc16-4,
										cc16-5, cc16-6, cc16-7, cc16-8,
										cc16-9, cc16-10, cc16-11, cc16-12,
										cc16-13, cc16-14, cc16-15, cc16-16 }

AccessServiceClass-TDD ::=			SEQUENCE {
	channelisationCodeIndices			BIT STRING	{
											chCodeIndex7(0),
											chCodeIndex6(1),
											chCodeIndex5(2),
											chCodeIndex4(3),
											chCodeIndex3(4),
											chCodeIndex2(5),
											chCodeIndex1(6),
											chCodeIndex0(7)
											} (SIZE(8))				OPTIONAL,
	subchannelSize						CHOICE {
		size1								NULL,
		size2								SEQUENCE {
			-- subch0 means bitstring '01' in the tabular, subch1 means bitsring '10'
			subchannels							ENUMERATED	{ subch0, subch1 }	OPTIONAL
		},
		size4								SEQUENCE {
			subchannels							BIT STRING	{
													subCh3(0), 
													subCh2(1), 
													subCh1(2), 
													subCh0(3) 
													} (SIZE(4))		OPTIONAL
		},
		size8								SEQUENCE {
			subchannels							BIT STRING	{
													subCh7(0), 
													subCh6(1), 
													subCh5(2), 
													subCh4(3), 
													subCh3(4), 
													subCh2(5), 
													subCh1(6), 
													subCh0(7) 
													} (SIZE(8))		OPTIONAL
		}
	}
}

TDD768-PRACH-CCode8 ::=				ENUMERATED {
										cc8-1, cc8-2, cc8-3, cc8-4,
										cc8-5, cc8-6, cc8-7, cc8-8 }

TDD768-PRACH-CCode16 ::=				ENUMERATED {
										cc16-1, cc16-2, cc16-3, cc16-4,
										cc16-5, cc16-6, cc16-7, cc16-8,
										cc16-9, cc16-10, cc16-11, cc16-12,
										cc16-13, cc16-14, cc16-15, cc16-16 }

TDD768-PRACH-CCode32 ::=				ENUMERATED {
										cc32-1, cc32-2, cc32-3, cc32-4,
										cc32-5, cc32-6, cc32-7, cc32-8,
										cc32-9, cc32-10, cc32-11, cc32-12,
										cc32-13, cc32-14, cc32-15, cc32-16 }

AccessServiceClass-TDD-r7 ::=			SEQUENCE {
	channelisationCodeIndices			BIT STRING	{
											chCodeIndex15(0),
											chCodeIndex14(1),
											chCodeIndex13(2),
											chCodeIndex12(3),
											chCodeIndex11(4),
											chCodeIndex10(5),
											chCodeIndex9(6),
											chCodeIndex8(7),
											chCodeIndex7(8),
											chCodeIndex6(9),
											chCodeIndex5(10),
											chCodeIndex4(11),
											chCodeIndex3(12),
											chCodeIndex2(13),
											chCodeIndex1(14),
											chCodeIndex0(15)
											} (SIZE(16))				OPTIONAL,
	subchannelSize						CHOICE {
		size1								NULL,
		size2								SEQUENCE {
			-- subch0 means bitstring '01' in the tabular, subch1 means bitsring '10'
			subchannels							ENUMERATED	{ subch0, subch1 }	OPTIONAL
		},
		size4								SEQUENCE {
			subchannels							BIT STRING	{
													subCh3(0), 
													subCh2(1), 
													subCh1(2), 
													subCh0(3) 
													} (SIZE(4))		OPTIONAL
		},
		size8								SEQUENCE {
			subchannels							BIT STRING	{
													subCh7(0), 
													subCh6(1), 
													subCh5(2), 
													subCh4(3), 
													subCh3(4), 
													subCh2(5), 
													subCh1(6), 
													subCh0(7) 
													} (SIZE(8))		OPTIONAL
		},
		size16								SEQUENCE {
			subchannels							BIT STRING	{
													subCh15(0), 
													subCh14(1), 
													subCh13(2), 
													subCh12(3), 
													subCh11(4), 
													subCh10(5), 
													subCh9(6), 
													subCh8(7),
													subCh7(8),
													subCh6(9),
													subCh5(10),
													subCh4(11),
													subCh3(12),
													subCh2(13),
													subCh1(14),
													subCh0(15) 
													} (SIZE(16))		OPTIONAL
		}
	}
}	

TimeslotNumber-PRACH-LCR-r4 ::=		INTEGER (1..6)

PRACH-ChanCodes-LCR-r4 ::=			SEQUENCE (SIZE (1..4)) OF
										TDD-PRACH-CCode-LCR-r4

FPACH-Info-r4 ::=						SEQUENCE {
	timeslot							TimeslotNumber-LCR-r4,
	channelisationCode					TDD-FPACH-CCode16-r4,
	midambleShiftAndBurstType			MidambleShiftAndBurstType-LCR-r4,
    wi                                  Wi-LCR
}

AccessServiceClass-TDD-LCR-r4 ::=	SEQUENCE {
	availableSYNC-UlCodesIndics		    BIT STRING {
											sulCodeIndex7(0),
											sulCodeIndex6(1),
											sulCodeIndex5(2),
											sulCodeIndex4(3),
											sulCodeIndex3(4),
											sulCodeIndex2(5),
											sulCodeIndex1(6),
											sulCodeIndex0(7)
											} (SIZE(8))               OPTIONAL,
	subchannelSize						CHOICE {
		size1								NULL,
		size2								SEQUENCE {
			-- subch0 means bitstring '01' in the tabular, subch1 means bitsring '10'.
			subchannels							ENUMERATED	{ subch0, subch1 }	OPTIONAL
		},
		size4								SEQUENCE {
			subchannels							BIT STRING	{
													subCh3(0), 
													subCh2(1), 
													subCh1(2), 
													subCh0(3) 
													} (SIZE(4))			OPTIONAL
		},
		size8								SEQUENCE {
			subchannels							BIT STRING	{
													subCh7(0), 
													subCh6(1), 
													subCh5(2), 
													subCh4(3), 
													subCh3(4), 
													subCh2(5), 
													subCh1(6), 
													subCh0(7) 
													} (SIZE(8))			OPTIONAL
		}
	}
	
}

RepetitionPeriodLengthAndOffset ::= CHOICE {
	repetitionPeriod1					NULL,
	repetitionPeriod2					SEQUENCE {
		length								NULL,
		offset								INTEGER (0..1)
	},
	repetitionPeriod4					SEQUENCE {
		length								INTEGER (1..3),
		offset								INTEGER (0..3)
	},
	repetitionPeriod8					SEQUENCE {
		length								INTEGER (1..7),
		offset								INTEGER (0..7)
	},
	repetitionPeriod16					SEQUENCE {
		length								INTEGER (1..15),
		offset								INTEGER (0..15)
	},
	repetitionPeriod32					SEQUENCE {
		length								INTEGER (1..31),
		offset								INTEGER (0..31)
	},
	repetitionPeriod64					SEQUENCE {
		length								INTEGER (1..63),
		offset								INTEGER (0..63)
	}
}

SCCPCH-ChannelisationCode ::=		ENUMERATED {
										cc16-1, cc16-2, cc16-3, cc16-4,
										cc16-5, cc16-6, cc16-7, cc16-8,
										cc16-9, cc16-10, cc16-11, cc16-12,
										cc16-13, cc16-14, cc16-15, cc16-16 }

MidambleConfigurationBurstType1and3 ::= ENUMERATED {ms4, ms8, ms16}

MidambleConfigurationBurstType2 ::=		ENUMERATED {ms3, ms6}

MidambleShiftShort ::=				INTEGER (0..5)

DL-TS-ChannelisationCode ::=		ENUMERATED {
										cc16-1, cc16-2, cc16-3, cc16-4,
										cc16-5, cc16-6, cc16-7, cc16-8,
										cc16-9, cc16-10, cc16-11, cc16-12,
										cc16-13, cc16-14, cc16-15, cc16-16 }

TFCI-Range ::=						SEQUENCE {
	maxTFCIField2Value					INTEGER (1..1023),
	tfcs-InfoForDSCH					TFCS-InfoForDSCH
}

TFCI-RangeList ::=					SEQUENCE (SIZE (1..maxPDSCH-TFCIgroups)) OF
										TFCI-Range

DedicatedDynamicTF-Info ::=			SEQUENCE {
	rlc-Size							CHOICE {
		bitMode								BitModeRLC-SizeInfo,
		octetModeType1						OctetModeRLC-SizeInfoType1
	},
	numberOfTbSizeList				SEQUENCE (SIZE (1..maxTF)) OF										NumberOfTransportBlocks,
	logicalChannelList				LogicalChannelList 
}

ChannelCodingType ::=				CHOICE { 
	-- noCoding is only used for TDD in this version of the specification,
	-- otherwise it should be ignored
	noCoding							NULL,
	convolutional						CodingRate,
	turbo								NULL 
}

RateMatchingAttribute ::=			INTEGER (1..hiRM)

CRC-Size ::=						ENUMERATED { 
										crc0, crc8, crc12, crc16, crc24 }

ReferenceTFC-ID ::=					INTEGER (0..3)										

UL-TS-ChannelisationCodeList-VHCR ::=	SEQUENCE (SIZE (1..2)) OF
											UL-TS-ChannelisationCode-VHCR

UplinkAdditionalTimeslots-LCR-r4 ::=	SEQUENCE {
	parameters							CHOICE {
		sameAsLast							SEQUENCE {
			timeslotNumber						TimeslotNumber
		},
		newParameters						SEQUENCE {
			individualTimeslotInfo						IndividualTimeslotInfo-LCR-r4,
			ul-TS-ChannelisationCodeList				UL-TS-ChannelisationCodeList
		}
	}
}

MidambleShiftAndBurstType-VHCR ::=	SEQUENCE {
	burstType							CHOICE {
		type1								SEQUENCE {
			midambleConfigurationBurstType1and3	MidambleConfigurationBurstType1and3,
			midambleAllocationMode				CHOICE {
				defaultMidamble						NULL,
				commonMidamble						NULL,
				ueSpecificMidamble					SEQUENCE {
					midambleShift						MidambleShiftLong
				}
			}
		},
		type2								SEQUENCE {
			midambleConfigurationBurstType2		MidambleConfigurationBurstType2-VHCR,
			midambleAllocationMode				CHOICE {
				defaultMidamble						NULL,
				commonMidamble						NULL,
				ueSpecificMidamble					SEQUENCE {
					midambleShift						MidambleShiftShort-VHCR
				}
			}
		},
		type3								SEQUENCE {
			midambleConfigurationBurstType1and3	MidambleConfigurationBurstType1and3,
			midambleAllocationMode				CHOICE {
				defaultMidamble						NULL,
				ueSpecificMidamble					SEQUENCE {
					midambleShift						MidambleShiftLong
				}
			}
		}
	}
}

DL-TS-ChannelisationCodesShort-VHCR ::=	SEQUENCE {
	codesRepresentation					CHOICE {
		consecutive							SEQUENCE {
			firstChannelisationCode				DL-TS-ChannelisationCode-VHCR,
			lastChannelisationCode				DL-TS-ChannelisationCode-VHCR
		},
		bitmap								BIT STRING {
												chCode32-SF32(0),
												chCode31-SF32(1),
												chCode30-SF32(2),
												chCode29-SF32(3),
												chCode28-SF32(4),
												chCode27-SF32(5),
												chCode26-SF32(6),
												chCode25-SF32(7),
												chCode24-SF32(8),
												chCode23-SF32(9),
												chCode22-SF32(10),
												chCode21-SF32(11),
												chCode20-SF32(12),
												chCode19-SF32(13),
												chCode18-SF32(14),
												chCode17-SF32(15),
												chCode16-SF32(16),
												chCode15-SF32(17),
												chCode14-SF32(18),
												chCode13-SF32(19),
												chCode12-SF32(20),
												chCode11-SF32(21),
												chCode10-SF32(22),
												chCode9-SF32(23),
												chCode8-SF32(24),
												chCode7-SF32(25),
												chCode6-SF32(26),
												chCode5-SF32(27),
												chCode4-SF32(28),
												chCode3-SF32(29),
												chCode2-SF32(30),
												chCode1-SF32(31)
												} 	(SIZE (32))
	}
}

DedicatedDynamicTF-Info-DynamicTTI ::= SEQUENCE {
	rlc-Size							CHOICE {
		bitMode								BitModeRLC-SizeInfo,
		octetModeType1						OctetModeRLC-SizeInfoType1
	},
	numberOfTbSizeAndTTIList			NumberOfTbSizeAndTTIList,
	logicalChannelList				LogicalChannelList 
}

CommonDynamicTF-Info-DynamicTTI ::=	SEQUENCE {
	commonTDD-Choice					CHOICE {
		bitModeRLC-SizeInfo					BitModeRLC-SizeInfo,
		octetModeRLC-SizeInfoType1			OctetModeRLC-SizeInfoType1
	},
	numberOfTbSizeAndTTIList			NumberOfTbSizeAndTTIList,
	logicalChannelList					LogicalChannelList
}

SCCPCH-ChannelisationCode-VHCR ::=	ENUMERATED {
										cc32-1, cc32-2, cc32-3, cc32-4,
										cc32-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

AvailableMinimumSF-VCAM ::=			SEQUENCE {
	minimumSpreadingFactor				MinimumSpreadingFactor,
	nf-Max								NF-Max,
	maxAvailablePCPCH-Number			MaxAvailablePCPCH-Number,
	availableAP-Signature-VCAMList		AvailableAP-Signature-VCAMList
}

PCP-Length ::=						ENUMERATED {
										as0, as8 }

UCSM-Info ::=						SEQUENCE {
	minimumSpreadingFactor				MinimumSpreadingFactor,
	nf-Max								NF-Max,
	channelReqParamsForUCSM				ChannelReqParamsForUCSM
}			

IntraFreqCellID ::=					INTEGER (0..maxCellMeas-1)

NewIntraFreqCellSI-RSCP ::=				SEQUENCE {
	intraFreqCellID						IntraFreqCellID						OPTIONAL,
	cellInfo							CellInfoSI-RSCP
}

IntraFreqMeasQuantity-TDD ::=		ENUMERATED {
										primaryCCPCH-RSCP,
										pathloss,
										timeslotISCP,
										dummy }

CellReportingQuantities ::=			SEQUENCE {
	-- dummy is not used in this version of the specification
	-- and if received it should be ignored.
	dummy					SFN-SFN-OTD-Type,
	cellIdentity-reportingIndicator						BOOLEAN,
	cellSynchronisationInfoReportingIndicator			BOOLEAN,
	modeSpecificInfo					CHOICE {
		fdd									SEQUENCE {
			cpich-Ec-N0-reportingIndicator							BOOLEAN,
			cpich-RSCP-reportingIndicator							BOOLEAN,
			pathloss-reportingIndicator							BOOLEAN
		},
		tdd									SEQUENCE {
			timeslotISCP-reportingIndicator						BOOLEAN,
			proposedTGSN-ReportingRequired						BOOLEAN,
			primaryCCPCH-RSCP-reportingIndicator					BOOLEAN,
			pathloss-reportingIndicator							BOOLEAN
		}
	}
}

IntraFreqReportingCriteria ::=		SEQUENCE {
	eventCriteriaList					IntraFreqEventCriteriaList		OPTIONAL
}

NewInterRATCell-B ::=				SEQUENCE {
	interRATCellID						InterRATCellID				OPTIONAL,
	technologySpecificInfo				CHOICE {
		gsm									SEQUENCE {
			cellSelectionReselectionInfo		CellSelectReselectInfoSIB-11-12		OPTIONAL,
			interRATCellIndividualOffset 		InterRATCellIndividualOffset,
			bsic								BSIC,
			frequency-band						Frequency-Band,
			bcch-ARFCN							BCCH-ARFCN,
			-- dummy is not used in this version of the specification, it should
			-- not be sent and if received it should be ignored.
			dummy								NULL				OPTIONAL
		},
		is-2000								SEQUENCE {
			is-2000SpecificMeasInfo				IS-2000SpecificMeasInfo
		},
		-- ASN.1 inconsistency: NewInterRATCellList-B should be optional within
		-- InterRATCellInfoList-B. The UE shall consider IE NewInterRATCell-B with
		-- technologySpecificInfo set to "absent" as valid and handle the
		-- message as if the IE NewInterRATCell-B was absent
		absent								NULL,
		spare1								NULL
	}
}

NewIntraFreqCellSI-HCS-ECN0 ::=		SEQUENCE {
	intraFreqCellID						IntraFreqCellID						OPTIONAL,
	cellInfo							CellInfoSI-HCS-ECN0
}

NewInterRATCell ::=				SEQUENCE {
	interRATCellID						InterRATCellID			OPTIONAL,
	technologySpecificInfo				CHOICE {
		gsm									SEQUENCE {
			cellSelectionReselectionInfo		CellSelectReselectInfoSIB-11-12		OPTIONAL,
			interRATCellIndividualOffset 		InterRATCellIndividualOffset,
			bsic								BSIC,
			frequency-band						Frequency-Band,
			bcch-ARFCN							BCCH-ARFCN,
			-- dummy is not used in this version of the specification, it should
			-- not be sent and if received it should be ignored.
			dummy								NULL				OPTIONAL
		},
		is-2000								SEQUENCE {
			is-2000SpecificMeasInfo				IS-2000SpecificMeasInfo
		},
		-- ASN.1 inconsistency: NewInterRATCellList should be optional within
		-- InterRATCellInfoList. The UE shall consider IE NewInterRATCell with
		-- technologySpecificInfo set to "absent" as valid and handle the
		-- message as if the IE NewInterRATCell was absent
		absent								NULL,
		spare1								NULL
	}
}

TransChCriteria ::=					SEQUENCE {
	ul-transportChannelID				UL-TrCH-Identity					OPTIONAL,
	eventSpecificParameters				SEQUENCE (SIZE (1..maxMeasParEvent)) OF 
											TrafficVolumeEventParam			OPTIONAL
}

ReportingIntervalLong ::=			ENUMERATED {
										ril0, ril0-25, ril0-5, ril1,
										ril2, ril3, ril4, ril6, ril8,
										ril12, ril16, ril20, ril24,
										ril28, ril32, ril64 }

NewIntraFreqCellSI-RSCP-LCR-r4 ::=		SEQUENCE {
	intraFreqCellID						IntraFreqCellID						OPTIONAL,
	cellInfo							CellInfoSI-RSCP-LCR-r4
}

IntraFreqReportingCriteria-LCR-r4 ::=	SEQUENCE {
	eventCriteriaList					IntraFreqEventCriteriaList-LCR-r4	OPTIONAL
}

NewIntraFreqCellSI-ECN0 ::=			SEQUENCE {
	intraFreqCellID						IntraFreqCellID						OPTIONAL,
	cellInfo							CellInfoSI-ECN0
}

InterRATCellID ::=				INTEGER (0..maxCellMeas-1)

NewIntraFreqCellSI-HCS-RSCP ::=		SEQUENCE {
	intraFreqCellID						IntraFreqCellID						OPTIONAL,
	cellInfo							CellInfoSI-HCS-RSCP
}

InterFreqCellID ::=					INTEGER (0..maxCellMeas-1)

NewInterFreqCellSI-HCS-ECN0-LCR-r4 ::=		SEQUENCE {
	interFreqCellID						InterFreqCellID						OPTIONAL,
	frequencyInfo						FrequencyInfo						OPTIONAL,
	cellInfo							CellInfoSI-HCS-ECN0-LCR-r4
}

NewIntraFreqCellSI-ECN0-LCR-r4 ::=		SEQUENCE {
	intraFreqCellID						IntraFreqCellID						OPTIONAL,
	cellInfo							CellInfoSI-ECN0-LCR-r4
}

NewInterFreqCellSI-HCS-RSCP-LCR-r4 ::=		SEQUENCE {
	interFreqCellID						InterFreqCellID						OPTIONAL,
	frequencyInfo						FrequencyInfo						OPTIONAL,
	cellInfo							CellInfoSI-HCS-RSCP-LCR-r4
}

RLC-InfoChoice ::=					CHOICE {
	rlc-Info							RLC-Info,
	same-as-RB							RB-Identity
}

RB-MappingInfo ::=					SEQUENCE (SIZE (1..maxRBMuxOptions)) OF
										RB-MappingOption

RB-Identity ::=						INTEGER (1..32)		

PDCP-Info ::=						SEQUENCE {
	losslessSRNS-RelocSupport			LosslessSRNS-RelocSupport			OPTIONAL,
	-- TABULAR: pdcp-PDU-Header is MD in the tabular format and it can be encoded
	-- in one bit, so the OPTIONAL is removed for compactness.
	pdcp-PDU-Header						PDCP-PDU-Header,
	headerCompressionInfoList			HeaderCompressionInfoList			OPTIONAL
}

TFC-Value ::=						INTEGER (0..1023)

AllowedTFC-List ::=					SEQUENCE (SIZE (1..maxTFC)) OF
										TFC-Value

Non-allowedTFC-List ::=				SEQUENCE (SIZE (1..maxTFC)) OF
										TFC-Value	

RestrictedTrChInfoList ::=			SEQUENCE (SIZE (1..maxTrCH)) OF
										RestrictedTrChInfo

IndividualUL-CCTrCH-Info ::=		SEQUENCE {
	ul-TFCS-Identity					TFCS-Identity,
	ul-TFCS								TFCS ,
	tfc-Subset							TFC-Subset
}		

UL-TrCH-Type ::=					ENUMERATED {dch, usch}

IndividualDL-CCTrCH-Info ::=		SEQUENCE {
	dl-TFCS-Identity					TFCS-Identity,
	tfcs-SignallingMode					CHOICE {
		explicit-config						TFCS,
		sameAsUL							TFCS-Identity
	}
}

DL-TrCH-Type ::=					ENUMERATED {dch, dsch}

UL-TransportChannelIdentity ::=		SEQUENCE {
	ul-TransportChannelType				UL-TrCH-Type,
	ul-TransportChannelIdentity			TransportChannelIdentity
}

QualityTarget ::=					SEQUENCE {
	bler-QualityValue					BLER-QualityValue
}

TM-SignallingInfo ::=				SEQUENCE {
	messType							MessType,
	tm-SignallingMode					CHOICE {
		mode1								NULL,
		mode2								SEQUENCE {
			-- in ul-controlledTrChList, TrCH-Type is always DCH
			ul-controlledTrChList				UL-ControlledTrChList
		}
	}
}

SF512-AndPilot ::=					CHOICE {
	sfd4								NULL, 
	sfd8								NULL, 
	sfd16								NULL, 
	sfd32								NULL,
	sfd64								NULL, 
	sfd128								PilotBits128, 
	sfd256								PilotBits256, 
	sfd512								NULL
}

Digit ::=							INTEGER (0..9)

UL-TS-ChannelisationCode ::=		ENUMERATED {
										cc1-1, cc2-1, cc2-2,
										cc4-1, cc4-2, cc4-3, cc4-4,
										cc8-1, cc8-2, cc8-3, cc8-4,
										cc8-5, cc8-6, cc8-7, cc8-8,
										cc16-1, cc16-2, cc16-3, cc16-4,
										cc16-5, cc16-6, cc16-7, cc16-8,
										cc16-9, cc16-10, cc16-11, cc16-12,
										cc16-13, cc16-14, cc16-15, cc16-16 }

TDD-PRACH-CCode-LCR-r4 ::=			ENUMERATED {
										cc4-1, cc4-2, cc4-3, cc4-4,
										cc8-1, cc8-2, cc8-3, cc8-4,
										cc8-5, cc8-6, cc8-7, cc8-8,
										cc16-1, cc16-2, cc16-3, cc16-4,
										cc16-5, cc16-6, cc16-7, cc16-8,
										cc16-9, cc16-10, cc16-11, cc16-12,
										cc16-13, cc16-14, cc16-15, cc16-16 }

TDD-FPACH-CCode16-r4 ::=			ENUMERATED {
										cc16-1, cc16-2, cc16-3, cc16-4,
										cc16-5, cc16-6, cc16-7, cc16-8,
										cc16-9, cc16-10, cc16-11, cc16-12,
										cc16-13, cc16-14, cc16-15, cc16-16 }

Wi-LCR ::=                                                               INTEGER(1..4)

NewInterFreqCellSI-RSCP ::=				SEQUENCE {
	interFreqCellID						InterFreqCellID						OPTIONAL,
	frequencyInfo						FrequencyInfo						OPTIONAL,
	cellInfo							CellInfoSI-RSCP
}

NewInterFreqCellSI-ECN0-LCR-r4 ::=			SEQUENCE {
	interFreqCellID						InterFreqCellID						OPTIONAL,
	frequencyInfo						FrequencyInfo						OPTIONAL,
	cellInfo							CellInfoSI-ECN0-LCR-r4
}

NewInterFreqCellSI-HCS-RSCP ::=				SEQUENCE {
	interFreqCellID						InterFreqCellID						OPTIONAL,
	frequencyInfo						FrequencyInfo						OPTIONAL,
	cellInfo							CellInfoSI-HCS-RSCP
}

NewInterFreqCellSI-RSCP-LCR-r4 ::=			SEQUENCE {
	interFreqCellID						InterFreqCellID						OPTIONAL,
	frequencyInfo						FrequencyInfo						OPTIONAL,
	cellInfo							CellInfoSI-RSCP-LCR-r4
}

TFCS-InfoForDSCH ::=				CHOICE {
	ctfc2bit							INTEGER (0..3),
	ctfc4bit							INTEGER (0..15),
	ctfc6bit							INTEGER (0..63),
	ctfc8bit							INTEGER (0..255),
	ctfc12bit							INTEGER (0..4095),
	ctfc16bit							INTEGER (0..65535),
	ctfc24bit							INTEGER (0..16777215)
}

BitModeRLC-SizeInfo ::=				CHOICE {
	sizeType1							INTEGER (0..127),
	-- Actual value sizeType2 = (part1 * 8) + 128 + part2
	sizeType2							SEQUENCE {
		part1								INTEGER (0..15),
		part2								INTEGER (1..7)					OPTIONAL
	},
	-- Actual value sizeType3 = (part1 * 16) + 256 + part2
	sizeType3							SEQUENCE {
		part1								INTEGER (0..47),
		part2								INTEGER (1..15)					OPTIONAL
	},
	-- Actual value sizeType4 = (part1 * 64) + 1024 + part2
	sizeType4							SEQUENCE {
		part1								INTEGER (0..62),
		part2								INTEGER (1..63)					OPTIONAL
	}
}

NumberOfTransportBlocks ::=			CHOICE {
	zero								NULL,
	one									NULL,
	small								INTEGER (2..17),
	large								INTEGER (18..512)
}

LogicalChannelList ::=				CHOICE {
		allSizes							NULL,
		configured							NULL,
		explicitList						SEQUENCE (SIZE (1..15)) OF
												LogicalChannelByRB				
}

CodingRate ::=						ENUMERATED {
										half,
										third }

UL-TS-ChannelisationCode-VHCR ::=		ENUMERATED {
										cc1-1, cc2-1, cc2-2,
										cc4-1, cc4-2, cc4-3, cc4-4,
										cc8-1, cc8-2, cc8-3, cc8-4,
										cc8-5, cc8-6, cc8-7, cc8-8,
										cc16-1, cc16-2, cc16-3, cc16-4,
										cc16-5, cc16-6, cc16-7, cc16-8,
										cc16-9, cc16-10, cc16-11, cc16-12,
										cc16-13, cc16-14, cc16-15, cc16-16,
										cc32-1, cc32-2, cc32-3, cc32-4,
										cc32-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

MidambleConfigurationBurstType2-VHCR ::=		ENUMERATED {ms4, ms8}

MidambleShiftShort-VHCR ::=			INTEGER (0..7)

DL-TS-ChannelisationCode-VHCR ::=	ENUMERATED {
										cc32-1, cc32-2, cc32-3, cc32-4,
										cc132-5, cc32-6, cc32-7, cc32-8,
										cc32-9, cc32-10, cc32-11, cc32-12,
										cc32-13, cc32-14, cc32-15, cc32-16,
										cc32-17, cc32-18, cc32-19, cc32-20,
										cc32-21, cc32-22, cc32-23, cc32-24,
										cc32-25, cc32-26, cc32-27, cc32-28,
										cc32-29, cc32-30, cc32-31, cc32-32 }

OctetModeRLC-SizeInfoType1 ::=		CHOICE {
	-- Actual size = (8 * sizeType1) + 16
	sizeType1							INTEGER (0..31),
	sizeType2							SEQUENCE {
		-- Actual size = (32 * part1) + 272 + (part2 * 8)
		part1								INTEGER (0..23),
		part2								INTEGER (1..3)					OPTIONAL
	},
	sizeType3							SEQUENCE {
		-- Actual size = (64 * part1) + 1040 + (part2 * 8)
		part1								INTEGER (0..61),
		part2								INTEGER (1..7)					OPTIONAL
	}
}

NumberOfTbSizeAndTTIList ::=		SEQUENCE (SIZE (1..maxTF)) OF SEQUENCE {
		numberOfTransportBlocks				NumberOfTransportBlocks,
		transmissionTimeInterval			TransmissionTimeInterval
}

NF-Max ::=							INTEGER (1..64)			

MaxAvailablePCPCH-Number ::=		INTEGER (1..64)

AvailableAP-Signature-VCAMList ::=	SEQUENCE (SIZE (1..maxPCPCH-APsig)) OF
										AP-Signature-VCAM

MinimumSpreadingFactor ::=			ENUMERATED {
										sf4, sf8, sf16, sf32,
										sf64, sf128, sf256 }

ChannelReqParamsForUCSM ::=			SEQUENCE {
	availableAP-SignatureList			AvailableAP-SignatureList,
	availableAP-SubchannelList			AvailableAP-SubchannelList			OPTIONAL
}

CellInfoSI-RSCP ::=					SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-RSCP		OPTIONAL
}

IntraFreqEventCriteriaList ::=		SEQUENCE (SIZE (1..maxMeasEvent)) OF
										IntraFreqEventCriteria

CellInfoSI-ECN0 ::=					SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-ECN0	OPTIONAL
}

CellSelectReselectInfoSIB-11-12 ::=	SEQUENCE {
	q-Offset1S-N						Q-OffsetS-N							DEFAULT 0,
	q-Offset2S-N						Q-OffsetS-N							OPTIONAL,
	maxAllowedUL-TX-Power				MaxAllowedUL-TX-Power				OPTIONAL,
	hcs-NeighbouringCellInformation-RSCP		HCS-NeighbouringCellInformation-RSCP		OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

BSIC ::=							SEQUENCE {
	ncc									NCC,
	bcc									BCC
}

Frequency-Band ::=					ENUMERATED {
										dcs1800BandUsed, pcs1900BandUsed }

BCCH-ARFCN ::=						INTEGER (0..1023)

IS-2000SpecificMeasInfo ::=			ENUMERATED {
										frequency, timeslot, colourcode,
										outputpower, pn-Offset }

CellInfoSI-HCS-RSCP ::=				SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-HCS-RSCP	OPTIONAL
}

CellInfoSI-HCS-ECN0 ::=				SEQUENCE {
	cellIndividualOffset				CellIndividualOffset		 		DEFAULT 0,
	referenceTimeDifferenceToCell		ReferenceTimeDifferenceToCell		OPTIONAL,
	modeSpecificInfo					CHOICE {
		fdd									SEQUENCE {
			primaryCPICH-Info					PrimaryCPICH-Info			OPTIONAL,
			primaryCPICH-TX-Power				PrimaryCPICH-TX-Power		OPTIONAL,
			readSFN-Indicator					BOOLEAN,
			tx-DiversityIndicator				BOOLEAN		
		},
		tdd									SEQUENCE {
			primaryCCPCH-Info					PrimaryCCPCH-Info,
			primaryCCPCH-TX-Power				PrimaryCCPCH-TX-Power		OPTIONAL,
			timeslotInfoList					TimeslotInfoList			OPTIONAL,
			readSFN-Indicator					BOOLEAN
		}
	},
	cellSelectionReselectionInfo		CellSelectReselectInfoSIB-11-12-HCS-ECN0	OPTIONAL
}

InterRATCellIndividualOffset ::=			INTEGER (-50..50)

TrafficVolumeEventParam ::=			SEQUENCE {
	eventID								TrafficVolumeEventType,
	reportingThreshold					TrafficVolumeThreshold,
	timeToTrigger						TimeToTrigger						OPTIONAL,
	pendingTimeAfterTrigger				PendingTimeAfterTrigger				OPTIONAL,
	tx-InterruptionAfterTrigger			TX-InterruptionAfterTrigger			OPTIONAL
}

CellInfoSI-RSCP-LCR-r4 ::=			SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-RSCP		OPTIONAL
}

IntraFreqEventCriteriaList-LCR-r4 ::=	SEQUENCE (SIZE (1..maxMeasEvent)) OF
										IntraFreqEventCriteria-LCR-r4

NewInterFreqCellSI-ECN0 ::=				SEQUENCE {
	interFreqCellID						InterFreqCellID						OPTIONAL,
	frequencyInfo						FrequencyInfo						OPTIONAL,
	cellInfo							CellInfoSI-ECN0
}

NewInterFreqCellSI-HCS-ECN0 ::=				SEQUENCE {
	interFreqCellID						InterFreqCellID						OPTIONAL,
	frequencyInfo						FrequencyInfo						OPTIONAL,
	cellInfo							CellInfoSI-HCS-ECN0
}

CellInfoSI-HCS-ECN0-LCR-r4 ::=		SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-HCS-ECN0	OPTIONAL
}

CellInfoSI-ECN0-LCR-r4 ::=			SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-ECN0	OPTIONAL
}

CellInfoSI-HCS-RSCP-LCR-r4 ::=		SEQUENCE {
	cellIndividualOffset				CellIndividualOffset		 		DEFAULT 0,
	referenceTimeDifferenceToCell		ReferenceTimeDifferenceToCell		OPTIONAL,
	primaryCCPCH-Info					PrimaryCCPCH-Info-LCR-r4,
	primaryCCPCH-TX-Power				PrimaryCCPCH-TX-Power				OPTIONAL,
	timeslotInfoList					TimeslotInfoList-LCR-r4				OPTIONAL,
	readSFN-Indicator					BOOLEAN,
	cellSelectionReselectionInfo		CellSelectReselectInfoSIB-11-12-HCS-RSCP	OPTIONAL
}

RLC-Info ::=						SEQUENCE {
	ul-RLC-Mode							UL-RLC-Mode							OPTIONAL,
	dl-RLC-Mode							DL-RLC-Mode							OPTIONAL
}

RB-MappingOption ::= 				SEQUENCE {
	ul-LogicalChannelMappings			UL-LogicalChannelMappings			OPTIONAL,
	dl-LogicalChannelMappingList		DL-LogicalChannelMappingList		OPTIONAL
}

LosslessSRNS-RelocSupport ::=		CHOICE {
	supported							MaxPDCP-SN-WindowSize,
	notSupported						NULL
}

PDCP-PDU-Header ::=					ENUMERATED {
										present, absent }

HeaderCompressionInfoList ::=		SEQUENCE (SIZE (1..maxPDCPAlgoType)) OF
										HeaderCompressionInfo

RestrictedTrChInfo ::=				SEQUENCE {
	ul-TransportChannelType				UL-TrCH-Type,
	restrictedTrChIdentity				TransportChannelIdentity,
	allowedTFI-List						AllowedTFI-List						OPTIONAL
}		

TFCS-Identity ::=					SEQUENCE {
	tfcs-ID								TFCS-IdentityPlain					DEFAULT 1,
	sharedChannelIndicator				BOOLEAN
}

-- Actual value BLER-QualityValue = IE value * 0.1
BLER-QualityValue ::=				INTEGER (-63..0)

MessType ::=						ENUMERATED {
										transportFormatCombinationControl }

UL-ControlledTrChList ::=			SEQUENCE (SIZE (1..maxTrCH)) OF
										TransportChannelIdentity

PilotBits128 ::=					ENUMERATED {
										pb4, pb8 }

PilotBits256 ::=					ENUMERATED {
										pb2, pb4, pb8 }

LogicalChannelByRB ::=				SEQUENCE {
	rb-Identity							RB-Identity,	
	logChOfRb							INTEGER (0..1)						OPTIONAL
}

TransmissionTimeInterval ::=		ENUMERATED {
										tti10, tti20, tti40, tti80 }

AP-Signature-VCAM ::=				SEQUENCE {
	ap-Signature						AP-Signature,
	availableAP-SubchannelList			AvailableAP-SubchannelList OPTIONAL
}


AvailableAP-SignatureList ::=		SEQUENCE (SIZE (1..maxPCPCH-APsig)) OF
										AP-Signature

AvailableAP-SubchannelList ::=		SEQUENCE (SIZE (1..maxPCPCH-APsubCh)) OF
										AP-Subchannel

ReferenceTimeDifferenceToCell ::= 	CHOICE {
	-- Actual value accuracy40 = IE value * 40
	accuracy40							INTEGER (0..960),
	-- Actual value accuracy256 = IE value * 256
	accuracy256							INTEGER (0..150),
	-- Actual value accuracy2560 = IE value * 2560
	accuracy2560						INTEGER (0..15)
}

TimeslotInfoList ::=				SEQUENCE (SIZE (1..maxTS)) OF
										TimeslotInfo

CellSelectReselectInfoSIB-11-12-RSCP ::=	SEQUENCE {
	q-OffsetS-N						Q-OffsetS-N						DEFAULT 0,
	maxAllowedUL-TX-Power				MaxAllowedUL-TX-Power				OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

IntraFreqEventCriteria ::=			SEQUENCE {
	event								IntraFreqEvent,
	hysteresis							Hysteresis,
	timeToTrigger						TimeToTrigger,
	reportingCellStatus					ReportingCellStatus					OPTIONAL
}

-- Actual value CellIndividualOffset = IE value * 0.5
CellIndividualOffset ::=			INTEGER (-20..20)

Q-OffsetS-N ::=						INTEGER (-50..50)

HCS-NeighbouringCellInformation-RSCP ::= SEQUENCE {
	hcs-PRIO							HCS-PRIO							DEFAULT 0,
	q-HCS								Q-HCS								DEFAULT 0,
	hcs-CellReselectInformation			HCS-CellReselectInformation-RSCP
}

BCC ::=								INTEGER (0..7)

SignalledGainFactors ::=			SEQUENCE {
	modeSpecificInfo					CHOICE {
		fdd									SEQUENCE {
			gainFactorBetaC						GainFactor
		},
		tdd									NULL
	},
	gainFactorBetaD						GainFactor,
	referenceTFC-ID						ReferenceTFC-ID						OPTIONAL
}

CommonDynamicTF-Info ::=			SEQUENCE {
	rlc-Size							CHOICE {
		fdd									SEQUENCE {
			octetModeRLC-SizeInfoType2			OctetModeRLC-SizeInfoType2
		},
		tdd									SEQUENCE {
			commonTDD-Choice					CHOICE {
				bitModeRLC-SizeInfo					BitModeRLC-SizeInfo,
				octetModeRLC-SizeInfoType1			OctetModeRLC-SizeInfoType1
			}
		}
	},
	numberOfTbSizeList				SEQUENCE (SIZE (1..maxTF)) OF		
											NumberOfTransportBlocks,
	logicalChannelList				LogicalChannelList
}

CellSelectReselectInfoSIB-11-12-ECN0 ::=	SEQUENCE {
	q-Offset1S-N						Q-OffsetS-N						DEFAULT 0,
	q-Offset2S-N						Q-OffsetS-N						DEFAULT 0,
	maxAllowedUL-TX-Power				MaxAllowedUL-TX-Power				OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-HCS-RSCP ::=	SEQUENCE {
	q-OffsetS-N						Q-OffsetS-N						DEFAULT 0,
	maxAllowedUL-TX-Power				MaxAllowedUL-TX-Power				OPTIONAL,
	hcs-NeighbouringCellInformation-RSCP		HCS-NeighbouringCellInformation-RSCP		OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

CellSelectReselectInfoSIB-11-12-HCS-ECN0 ::=	SEQUENCE {
	q-Offset1S-N						Q-OffsetS-N						DEFAULT 0,
	q-Offset2S-N						Q-OffsetS-N						DEFAULT 0,
	maxAllowedUL-TX-Power				MaxAllowedUL-TX-Power				OPTIONAL,
	hcs-NeighbouringCellInformation-ECN0		HCS-NeighbouringCellInformation-ECN0		OPTIONAL,
	modeSpecificInfo					CHOICE {
		fdd									SEQUENCE {
			q-QualMin							Q-QualMin					OPTIONAL,
			q-RxlevMin							Q-RxlevMin					OPTIONAL
		},
		tdd									SEQUENCE {
			q-RxlevMin							Q-RxlevMin					OPTIONAL
		},
		gsm									SEQUENCE {
			q-RxlevMin							Q-RxlevMin					OPTIONAL
		}
	}
}

TrafficVolumeEventType ::=			ENUMERATED {
										e4a,
										e4b }

TrafficVolumeThreshold ::=			ENUMERATED {
										th8, th16, th32, th64, th128,
										th256, th512, th1024, th2k, th3k, 
										th4k, th6k, th8k, th12k, th16k, 
										th24k, th32k, th48k, th64k, th96k, 
										th128k, th192k, th256k, th384k, 
										th512k, th768k }

TimeToTrigger ::=					ENUMERATED {
										ttt0, ttt10, ttt20, ttt40, ttt60,
										ttt80, ttt100, ttt120, ttt160,
										ttt200, ttt240, tt320, ttt640,
										ttt1280, ttt2560, ttt5000 }

PendingTimeAfterTrigger ::=			ENUMERATED {
										ptat0-25, ptat0-5, ptat1,
										ptat2, ptat4, ptat8, ptat16 }

TX-InterruptionAfterTrigger ::=		ENUMERATED {
										txiat0-25, txiat0-5, txiat1,
										txiat2, txiat4, txiat8, txiat16 }

IntraFreqEventCriteria-LCR-r4 ::=	SEQUENCE {
	event								IntraFreqEvent-LCR-r4,
	hysteresis							Hysteresis,
	timeToTrigger						TimeToTrigger,
	reportingCellStatus					ReportingCellStatus					OPTIONAL
}

PrimaryCCPCH-Info-LCR-r4 ::=		SEQUENCE {
	tstd-Indicator						BOOLEAN,
	cellParametersID					CellParametersID				OPTIONAL,
	sctd-Indicator						BOOLEAN
}

TimeslotInfoList-LCR-r4 ::=			SEQUENCE (SIZE (1..maxTS-LCR)) OF
										TimeslotInfo-LCR-r4

UL-RLC-Mode ::=						CHOICE {
	ul-AM-RLC-Mode						UL-AM-RLC-Mode,
	ul-UM-RLC-Mode						UL-UM-RLC-Mode,
	ul-TM-RLC-Mode						UL-TM-RLC-Mode,
	spare								NULL
}

DL-RLC-Mode ::=						CHOICE {
	dl-AM-RLC-Mode						DL-AM-RLC-Mode,
	dl-UM-RLC-Mode						NULL,
	dl-TM-RLC-Mode						DL-TM-RLC-Mode
}

UL-LogicalChannelMappings ::=		CHOICE {
	oneLogicalChannel					UL-LogicalChannelMapping,
	twoLogicalChannels					UL-LogicalChannelMappingList
}

DL-LogicalChannelMappingList ::=	SEQUENCE (SIZE (1..maxLoCHperRLC)) OF
										DL-LogicalChannelMapping


MaxPDCP-SN-WindowSize ::=			ENUMERATED {
										sn255, sn65535 }

HeaderCompressionInfo ::=			SEQUENCE {
	algorithmSpecificInfo				AlgorithmSpecificInfo
}

AllowedTFI-List ::=					SEQUENCE (SIZE (1..maxTF)) OF
										INTEGER (0..31)

AP-Signature ::=					INTEGER (0..15)

AP-Subchannel ::=					INTEGER (0..11)

TimeslotInfo ::=					SEQUENCE {
	timeslotNumber						TimeslotNumber,
	burstType							BurstType
}

IntraFreqEvent ::=					CHOICE {
	e1a									Event1a,
	e1b									Event1b,
	e1c									Event1c,
	e1d									NULL,
	e1e									Event1e,
	e1f									Event1f,
	e1g									NULL,
	e1h									ThresholdUsedFrequency,
	e1i									ThresholdUsedFrequency
}

ReportingCellStatus ::=				CHOICE{
	withinActiveSet						MaxNumberOfReportingCellsType1,
	withinMonitoredSetUsedFreq			MaxNumberOfReportingCellsType1,
	withinActiveAndOrMonitoredUsedFreq	MaxNumberOfReportingCellsType1,
	withinDetectedSetUsedFreq			MaxNumberOfReportingCellsType1,
	withinMonitoredAndOrDetectedUsedFreq
										MaxNumberOfReportingCellsType1,
	allActiveplusMonitoredSet			MaxNumberOfReportingCellsType3,
	allActivePlusDetectedSet			MaxNumberOfReportingCellsType3,
	allActivePlusMonitoredAndOrDetectedSet
										MaxNumberOfReportingCellsType3,
	withinVirtualActSet				MaxNumberOfReportingCellsType1,
	withinMonitoredSetNonUsedFreq		MaxNumberOfReportingCellsType1,
	withinMonitoredAndOrVirtualActiveSetNonUsedFreq
										MaxNumberOfReportingCellsType1,
	allVirtualActSetplusMonitoredSetNonUsedFreq	
										MaxNumberOfReportingCellsType3,
	withinActSetOrVirtualActSet-InterRATcells
										MaxNumberOfReportingCellsType2,
	withinActSetAndOrMonitoredUsedFreqOrVirtualActSetAndOrMonitoredNonUsedFreq	
										MaxNumberOfReportingCellsType2
}

-- Actual value Hysteresis = IE value * 0.5
Hysteresis ::=						INTEGER (0..15)

HCS-CellReselectInformation-RSCP ::=		SEQUENCE {
	-- TABULAR: The default value for penaltyTime is "notUsed"
	-- Temporary offset is nested inside PenaltyTime-RSCP
	penaltyTime									PenaltyTime-RSCP
}

GainFactor ::=						INTEGER (0..15)

HCS-NeighbouringCellInformation-ECN0 ::= SEQUENCE {
	hcs-PRIO							HCS-PRIO							DEFAULT 0,
	q-HCS								Q-HCS								DEFAULT 0,
	hcs-CellReselectInformation			HCS-CellReselectInformation-ECN0
}

TimeslotInfo-LCR-r4 ::=				SEQUENCE {
	timeslotNumber						TimeslotNumber-LCR-r4
}

IntraFreqEvent-LCR-r4 ::=			CHOICE {
	e1a									Event1a-LCR-r4,
	e1b									Event1b-LCR-r4,
	e1c									Event1c,
	e1d									NULL,
	e1e									Event1e,
	e1f									Event1f,
	e1g									NULL,
	e1h									ThresholdUsedFrequency,
	e1i									ThresholdUsedFrequency
}

-- Actual value FineSFN-SFN = IE value * 0.0625
FineSFN-SFN ::=						INTEGER (0..15)

AccessServiceClass-FDD ::=			SEQUENCE {
	availableSignatureStartIndex		INTEGER (0..15),
	availableSignatureEndIndex			INTEGER (0..15),

	assignedSubChannelNumber			BIT STRING {
											b3(0),
											b2(1),
											b1(2),
											b0(3)
											}	 (SIZE(4))
}

UL-AM-RLC-Mode ::=					SEQUENCE {
	transmissionRLC-Discard				TransmissionRLC-Discard,
	transmissionWindowSize				TransmissionWindowSize,
	timerRST							TimerRST,
	max-RST								MaxRST,
	pollingInfo							PollingInfo							OPTIONAL
}

UL-UM-RLC-Mode ::=					SEQUENCE {
	transmissionRLC-Discard				TransmissionRLC-Discard				OPTIONAL
}

UL-TM-RLC-Mode ::=					SEQUENCE {
	transmissionRLC-Discard				TransmissionRLC-Discard				OPTIONAL,
	segmentationIndication				BOOLEAN
}

UL-LogicalChannelMapping ::=		SEQUENCE {
	-- TABULAR: UL-TransportChannelType contains TransportChannelIdentity as well.
	ul-TransportChannelType				UL-TransportChannelType,
	logicalChannelIdentity				LogicalChannelIdentity				OPTIONAL,
	rlc-SizeList						CHOICE {
		allSizes							NULL,
		configured							NULL,
		explicitList						RLC-SizeExplicitList
	},
	mac-LogicalChannelPriority			MAC-LogicalChannelPriority
}

UL-LogicalChannelMappingList ::=	SEQUENCE {
	-- rlc-LogicalChannelMappingIndicator shall be set to TRUE in this version
	-- of the specification
	rlc-LogicalChannelMappingIndicator	BOOLEAN,
	ul-LogicalChannelMapping			SEQUENCE (SIZE (maxLoCHperRLC)) OF
										UL-LogicalChannelMapping
}

DL-LogicalChannelMapping ::=		SEQUENCE {
	-- TABULAR: DL-TransportChannelType contains TransportChannelIdentity as well.
	dl-TransportChannelType				DL-TransportChannelType,
	logicalChannelIdentity				LogicalChannelIdentity				OPTIONAL
}

AlgorithmSpecificInfo ::=			CHOICE {
	rfc2507-Info						RFC2507-Info
}

Event1a ::=							SEQUENCE {
	triggeringCondition					TriggeringCondition2,
	reportingRange						ReportingRange,
	forbiddenAffectCellList				ForbiddenAffectCellList				OPTIONAL,
	w									W,
	reportDeactivationThreshold			ReportDeactivationThreshold,
	reportingAmount						ReportingAmount,
	reportingInterval					ReportingInterval
}

Event1b ::=							SEQUENCE {
	triggeringCondition					TriggeringCondition1,
	reportingRange						ReportingRange,
	forbiddenAffectCellList				ForbiddenAffectCellList				OPTIONAL,
	w									W
}

Event1c ::=							SEQUENCE {
	replacementActivationThreshold		ReplacementActivationThreshold,
	reportingAmount						ReportingAmount,
	reportingInterval					ReportingInterval
}

Event1e ::=						SEQUENCE {
	triggeringCondition					TriggeringCondition2,
	thresholdUsedFrequency				ThresholdUsedFrequency
}

Event1f ::=						SEQUENCE {
	triggeringCondition					TriggeringCondition1,
	thresholdUsedFrequency				ThresholdUsedFrequency
}

ThresholdUsedFrequency ::=			INTEGER (-115..165)

MaxNumberOfReportingCellsType1 ::=	ENUMERATED {
										e1, e2, e3, e4, e5, e6}

DL-AM-RLC-Mode ::=					SEQUENCE {
	inSequenceDelivery					BOOLEAN,
	receivingWindowSize					ReceivingWindowSize,
	dl-RLC-StatusInfo					DL-RLC-StatusInfo
}

DL-TM-RLC-Mode ::=					SEQUENCE {
	segmentationIndication					BOOLEAN
}

MaxNumberOfReportingCellsType3 ::=	ENUMERATED {
										viactCellsPlus1,
										viactCellsPlus2,
										viactCellsPlus3,
										viactCellsPlus4,
										viactCellsPlus5,
										viactCellsPlus6 }

PenaltyTime-RSCP ::=				CHOICE {
	notUsed								NULL,
	pt10								TemporaryOffset1,
	pt20								TemporaryOffset1,
	pt30								TemporaryOffset1,
	pt40								TemporaryOffset1,
	pt50								TemporaryOffset1,
	pt60								TemporaryOffset1
}

HCS-CellReselectInformation-ECN0 ::=		SEQUENCE {
	-- TABULAR: The default value for penaltyTime is "notUsed"
	-- Temporary offset is nested inside PenaltyTime-ECN0
	penaltyTime							PenaltyTime-ECN0
}

Event1a-LCR-r4 ::=					SEQUENCE {
	triggeringCondition					TriggeringCondition2,
	reportingRange						ReportingRange,
	forbiddenAffectCellList				ForbiddenAffectCellList-LCR-r4			OPTIONAL,
	w									W,
	reportDeactivationThreshold			ReportDeactivationThreshold,
	reportingAmount						ReportingAmount,
	reportingInterval					ReportingInterval
}

TransmissionWindowSize ::=			ENUMERATED {
										tw1, tw8, tw16, tw32, tw64, tw128, tw256,
										tw512, tw768, tw1024, tw1536, tw2047, 
										tw2560, tw3072, tw3584, tw4095 }

TimerRST ::=						ENUMERATED {
										tr50, tr100, tr150, tr200, tr250, tr300, 
										tr350, tr400, tr450, tr500, tr550,
										tr600, tr700, tr800, tr900, tr1000 }

MaxRST ::=							ENUMERATED {
										rst1, rst4, rst6, rst8, rst12,
										rst16, rst24, rst32 }

PollingInfo ::=						SEQUENCE {
	timerPollProhibit					TimerPollProhibit					OPTIONAL,
	timerPoll							TimerPoll							OPTIONAL,
	poll-PDU							Poll-PDU							OPTIONAL,
	poll-SDU							Poll-SDU							OPTIONAL,
	lastTransmissionPDU-Poll			BOOLEAN,
	lastRetransmissionPDU-Poll			BOOLEAN,
	pollWindow							PollWindow							OPTIONAL,
	timerPollPeriodic					TimerPollPeriodic					OPTIONAL
}

TransmissionRLC-Discard ::=			CHOICE {
	timerBasedExplicit					ExplicitDiscard,
	timerBasedNoExplicit				NoExplicitDiscard,
	maxDAT-Retransmissions				MaxDAT-Retransmissions,
	noDiscard							MaxDAT
}

UL-TransportChannelType ::=			CHOICE {
	dch									TransportChannelIdentity,
	rach								NULL,
	-- dummy is not used in this version of the specification and
	-- if received the UE behaviour is not specified.
	dummy								NULL,
	usch								TransportChannelIdentity
}

RLC-SizeExplicitList ::=			SEQUENCE (SIZE	(1..maxTF))	OF
										RLC-SizeInfo

MAC-LogicalChannelPriority ::= 		INTEGER (1..8)

DL-TransportChannelType ::=			CHOICE {
	dch									TransportChannelIdentity,
	fach								NULL,
	-- The choice “dsch” should not be used in FDD mode, and if received
	-- the UE behaviour is unspecified.
	dsch								TransportChannelIdentity,
	-- The choice “dch-and-dsch” should not be used in FDD mode, and if received the UE
	-- behaviour is unspecified
	dch-and-dsch						TransportChannelIdentityDCHandDSCH
}

LogicalChannelIdentity ::=			INTEGER (1..15)

RFC2507-Info ::=					SEQUENCE {
	f-MAX-PERIOD						INTEGER (1..65535)					DEFAULT 256,
	f-MAX-TIME							INTEGER (1..255)					DEFAULT 5,
	max-HEADER							INTEGER (60..65535)					DEFAULT 168,
	tcp-SPACE							INTEGER (3..255)					DEFAULT 15,
	non-TCP-SPACE						INTEGER (3..65535)					DEFAULT 15,
	-- TABULAR: expectReordering has only two possible values, so using Optional or Default
	-- would be wasteful
	expectReordering					ExpectReordering
}

-- Actual value ReportingRange = IE value * 0.5
ReportingRange ::=					INTEGER (0..29)

ForbiddenAffectCellList ::=			SEQUENCE (SIZE (1..maxCellMeas)) OF
										ForbiddenAffectCell

-- Actual value W = IE value * 0.1
W ::=								INTEGER (0..20)		

ReportDeactivationThreshold ::=		ENUMERATED {
										notApplicable, t1, t2,
										t3, t4, t5, t6, t7 }

TriggeringCondition1 ::=			ENUMERATED {
										activeSetCellsOnly,
										monitoredSetCellsOnly,
										activeSetAndMonitoredSetCells }
	
ReplacementActivationThreshold ::= 	ENUMERATED {
										notApplicable, t1, t2,
										t3, t4, t5, t6, t7 }

MaxNumberOfReportingCellsType2 ::=	ENUMERATED {
										e1, e2, e3, e4, e5, e6, e7, e8, e9, e10, e11, e12}

Event1b-LCR-r4 ::=					SEQUENCE {
	triggeringCondition					TriggeringCondition1,
	reportingRange						ReportingRange,
	forbiddenAffectCellList				ForbiddenAffectCellList-LCR-r4			OPTIONAL,
	w									W
}

ReceivingWindowSize ::=				ENUMERATED {
										rw1, rw8, rw16, rw32, rw64, rw128, rw256,
										rw512, rw768, rw1024, rw1536, rw2047, 
										rw2560, rw3072, rw3584, rw4095 }

DL-RLC-StatusInfo ::=				SEQUENCE {
	timerStatusProhibit					TimerStatusProhibit					OPTIONAL,
	-- dummy is not used in this version of the specification, it should not be sent 
	-- and if received they should be ignored.
	dummy							TimerEPC							OPTIONAL,
	missingPDU-Indicator					BOOLEAN,
	timerStatusPeriodic					TimerStatusPeriodic					OPTIONAL
}

TemporaryOffset1 ::=				ENUMERATED {
										to3, to6, to9, to12, to15,
										to18, to21, infinite }

PenaltyTime-ECN0 ::=				CHOICE {
	notUsed								NULL,
	pt10								TemporaryOffsetList,
	pt20								TemporaryOffsetList,
	pt30								TemporaryOffsetList,
	pt40								TemporaryOffsetList,
	pt50								TemporaryOffsetList,
	pt60								TemporaryOffsetList
}	

ForbiddenAffectCellList-LCR-r4 ::=	SEQUENCE (SIZE (1..maxCellMeas)) OF
										ForbiddenAffectCell-LCR-r4

NoExplicitDiscard ::=				ENUMERATED {
										dt10, dt20, dt30, dt40, dt50,
										dt60, dt70, dt80, dt90, dt100 }

MaxDAT-Retransmissions ::=			SEQUENCE {
	maxDAT								MaxDAT,
	timerMRW							TimerMRW,
	maxMRW								MaxMRW
}

MaxDAT ::=							ENUMERATED {
										dat1, dat2, dat3, dat4, dat5, dat6,
										dat7, dat8, dat9, dat10, dat15, dat20,
										dat25, dat30, dat35, dat40 }

TimerPollProhibit ::=				ENUMERATED {
										tpp10, tpp20, tpp30, tpp40, tpp50,
										tpp60, tpp70, tpp80, tpp90, tpp100,
										tpp110, tpp120, tpp130, tpp140, tpp150,
										tpp160, tpp170, tpp180, tpp190, tpp200,
										tpp210, tpp220, tpp230, tpp240, tpp250,
										tpp260, tpp270, tpp280, tpp290, tpp300,
										tpp310, tpp320, tpp330, tpp340, tpp350,
										tpp360, tpp370, tpp380, tpp390, tpp400,
										tpp410, tpp420, tpp430, tpp440, tpp450,
										tpp460, tpp470, tpp480, tpp490, tpp500,
										tpp510, tpp520, tpp530, tpp540, tpp550,
										tpp600, tpp650, tpp700, tpp750, tpp800,
										tpp850, tpp900, tpp950, tpp1000 }

TimerPoll ::=						ENUMERATED {
										tp10, tp20, tp30, tp40, tp50,
										tp60, tp70, tp80, tp90, tp100,
										tp110, tp120, tp130, tp140, tp150,
										tp160, tp170, tp180, tp190, tp200,
										tp210, tp220, tp230, tp240, tp250,
										tp260, tp270, tp280, tp290, tp300,
										tp310, tp320, tp330, tp340, tp350,
										tp360, tp370, tp380, tp390, tp400,
										tp410, tp420, tp430, tp440, tp450,
										tp460, tp470, tp480, tp490, tp500,
										tp510, tp520, tp530, tp540, tp550,
										tp600, tp650, tp700, tp750, tp800,
										tp850, tp900, tp950, tp1000 }

Poll-PDU ::=						ENUMERATED {
										pdu1, pdu2, pdu4, pdu8, pdu16, 
										pdu32, pdu64, pdu128 }

PollWindow ::=						ENUMERATED {
										pw50, pw60, pw70, pw80, pw85, 
										pw90, pw95, pw99 }

TimerPollPeriodic ::=				ENUMERATED {
										tper100, tper200, tper300, tper400,
										tper500, tper750, tper1000, tper2000 }

ExplicitDiscard ::=					SEQUENCE {
	timerMRW							TimerMRW,
	timerDiscard						TimerDiscard,
	maxMRW								MaxMRW
}	

Poll-SDU ::=						ENUMERATED {
										sdu1, sdu4, sdu16, sdu64 }
			
RLC-SizeInfo ::=					SEQUENCE {
	rlc-SizeIndex						INTEGER (1..maxTF)
}

NewIntraFreqCellSI-List-ECN0-LCR-r4 ::=		SEQUENCE (SIZE (1..maxCellMeas)) OF
										NewIntraFreqCellSI-ECN0-LCR-r4

NewIntraFreqCellSI-HCS-RSCP-LCR-r4 ::=	SEQUENCE {
	intraFreqCellID						IntraFreqCellID						OPTIONAL,
	cellInfo							CellInfoSI-HCS-RSCP-LCR-r4
}

NewIntraFreqCellSI-HCS-ECN0-LCR-r4 ::=	SEQUENCE {
	intraFreqCellID						IntraFreqCellID						OPTIONAL,
	cellInfo							CellInfoSI-HCS-ECN0-LCR-r4
}

TransportChannelIdentityDCHandDSCH ::=	SEQUENCE {
	dch-transport-ch-id				TransportChannelIdentity,
	dsch-transport-ch-id			TransportChannelIdentity
}

ExpectReordering ::=				ENUMERATED {
										reorderingNotExpected,
										reorderingExpected }

ForbiddenAffectCell ::=				CHOICE {
	fdd									PrimaryCPICH-Info,
	tdd									PrimaryCCPCH-Info
}

TimerStatusProhibit ::=				ENUMERATED {
										tsp10,tsp20,tsp30,tsp40,tsp50,
										tsp60,tsp70,tsp80,tsp90,tsp100,
										tsp110,tsp120,tsp130,tsp140,tsp150,
										tsp160,tsp170,tsp180,tsp190,tsp200,
										tsp210,tsp220,tsp230,tsp240,tsp250,
										tsp260,tsp270,tsp280,tsp290,tsp300,
										tsp310,tsp320,tsp330,tsp340,tsp350,
										tsp360,tsp370,tsp380,tsp390,tsp400,
										tsp410,tsp420,tsp430,tsp440,tsp450,
										tsp460,tsp470,tsp480,tsp490,tsp500,
										tsp510,tsp520,tsp530,tsp540,tsp550,
										tsp600,tsp650,tsp700,tsp750,tsp800,
										tsp850,tsp900,tsp950,tsp1000 }

TimerEPC ::=						ENUMERATED {
										te50, te60, te70, te80, te90,
										te100, te120, te140, te160, te180,
										te200, te300, te400, te500, te700,
										te900 }
			
TimerStatusPeriodic ::=				ENUMERATED {
										tsp100, tsp200,	tsp300, tsp400, tsp500,
										tsp750, tsp1000, tsp2000 }
		
TemporaryOffsetList ::=				SEQUENCE 	{
		temporaryOffset1 				TemporaryOffset1,
		temporaryOffset2 				TemporaryOffset2
}
	
ForbiddenAffectCell-LCR-r4 ::=		SEQUENCE {
	tdd									PrimaryCCPCH-Info-LCR-r4
}

TimerDiscard ::=					ENUMERATED {
										td0-1, td0-25, td0-5, td0-75,
										td1, td1-25, td1-5, td1-75,
										td2, td2-5, td3, td3-5, td4,
										td4-5, td5, td7-5 }

MaxMRW ::=							ENUMERATED {
										mm1, mm4, mm6, mm8, mm12, mm16,
										mm24, mm32 }	
										
TimerMRW ::=						ENUMERATED {
										te50, te60, te70, te80, te90, te100, 
										te120, te140, te160, te180, te200, 
										te300, te400, te500, te700, te900 }

TemporaryOffset2 ::=				ENUMERATED {
										to2, to3, to4, to6, to8,
										to10, to12, infinite }																			
END


Constant-definitions DEFINITIONS AUTOMATIC TAGS ::=

BEGIN

hiPDSCHidentities			INTEGER ::= 64
hiPUSCHidentities			INTEGER ::= 64
hiRM						INTEGER ::= 256
maxAC						INTEGER ::= 16
maxAdditionalMeas 			INTEGER ::= 4
maxASC						INTEGER ::= 8
maxASCmap					INTEGER ::= 7
maxASCpersist				INTEGER ::= 6
maxCCTrCH					INTEGER ::= 8
maxCellMeas 				INTEGER ::= 32
maxCellMeas-1				INTEGER ::= 31
maxCNdomains				INTEGER ::= 4
maxCPCHsets					INTEGER ::= 16
maxDPCH-DLchan				INTEGER ::= 8
maxDPDCH-UL					INTEGER ::= 6
maxDRACclasses				INTEGER ::= 8
maxE-DCHMACdFlow			INTEGER ::= 8
maxE-DCHMACdFlow-1			INTEGER ::= 7
maxEDCHRL					INTEGER ::= 4
maxFACHPCH					INTEGER ::= 8
maxFreq						INTEGER ::= 8
maxFreqBandsFDD				INTEGER ::= 8
maxFreqBandsFDD-ext			INTEGER ::= 15	-- maxFreqBandsFDD-ext ::= 22 – (maxFreqBandsFDD – 1)
maxFreqBandsTDD				INTEGER ::= 4
maxFreqBandsGSM				INTEGER ::= 16
maxGERAN-SI					INTEGER ::= 8
maxGSMTargetCells			INTEGER ::= 32
maxHProcesses 				INTEGER ::= 8
maxHSDSCHTBIndex			INTEGER ::= 64
maxHSDSCHTBIndex-tdd384		INTEGER ::= 512
maxHSSCCHs					INTEGER ::= 4
maxInterSysMessages 		INTEGER ::= 4
maxLoCHperRLC				INTEGER ::= 2
maxMAC-d-PDUsizes			INTEGER ::= 8
maxMBMS-CommonCCTrCh		INTEGER ::= 32
maxMBMS-CommonPhyCh			INTEGER ::= 32
maxMBMS-CommonRB			INTEGER ::= 32
maxMBMS-CommonTrCh			INTEGER ::= 32
maxMBMS-Freq				INTEGER ::= 4
maxMBMS-L1CP				INTEGER ::= 4
maxMBMSservCount			INTEGER ::= 8
maxMBMSservModif			INTEGER ::= 32
maxMBMSservSched			INTEGER ::= 16
maxMBMSservUnmodif			INTEGER ::= 64
maxMBMSTransmis				INTEGER ::= 4
maxMeasEvent				INTEGER ::= 8
maxMeasIntervals			INTEGER ::= 3
maxMeasParEvent				INTEGER ::= 2
maxNumCDMA2000Freqs			INTEGER ::=  8
maxNumGSMFreqRanges			INTEGER ::= 32
maxNumFDDFreqs				INTEGER ::=  8
maxNumTDDFreqs				INTEGER ::=  8
maxNoOfMeas					INTEGER ::= 16
maxOtherRAT					INTEGER ::= 15
maxOtherRAT-16				INTEGER ::= 16
maxPage1					INTEGER ::= 8
maxPCPCH-APsig				INTEGER ::= 16
maxPCPCH-APsubCh			INTEGER ::= 12
maxPCPCH-CDsig				INTEGER ::= 16
maxPCPCH-CDsubCh			INTEGER ::= 12
maxPCPCH-SF					INTEGER ::= 7
maxPCPCHs					INTEGER ::= 64
maxPDCPAlgoType				INTEGER ::= 8
maxPDSCH					INTEGER ::= 8
maxPDSCH-TFCIgroups	 		INTEGER ::= 256
maxPRACH					INTEGER ::= 16
maxPRACH-FPACH				INTEGER ::= 8
maxPredefConfig				INTEGER ::= 16
maxPUSCH					INTEGER ::= 8
maxQueueIDs					INTEGER ::= 8
maxRABsetup					INTEGER ::= 16
maxRAT						INTEGER ::= 16
maxRB						INTEGER ::= 32
maxRBallRABs				INTEGER ::= 27
maxRBMuxOptions				INTEGER ::= 8
maxRBperRAB					INTEGER ::= 8
maxRBperTrCh				INTEGER ::= 16
maxReportedGSMCells			INTEGER ::= 8
maxRL						INTEGER ::= 8
maxRL-1						INTEGER ::= 7
maxRLCPDUsizePerLogChan		INTEGER ::= 32
maxRFC3095-CID				INTEGER ::= 16384
maxROHC-PacketSizes-r4		INTEGER ::= 16
maxROHC-Profile-r4			INTEGER ::= 8
maxSat						INTEGER ::= 16
maxSCCPCH					INTEGER ::= 16
maxSIB						INTEGER ::= 32
maxSIB-FACH					INTEGER ::= 8
maxSIBperMsg				INTEGER ::= 16
maxSRBsetup					INTEGER ::= 8
maxSystemCapability			INTEGER ::= 16
maxTF						INTEGER ::= 32
maxTF-CPCH					INTEGER ::= 16
maxTFC						INTEGER ::= 1024
maxTFCsub					INTEGER ::= 1024
maxTFCI-2-Combs	 			INTEGER ::= 512
maxTGPS						INTEGER ::= 6
maxTrCH						INTEGER ::= 32
-- maxTrCHpreconf should be 16 but has been set to 32 for compatibility
maxTrCHpreconf				INTEGER ::= 32
maxTS						INTEGER ::= 14
maxTS-1						INTEGER ::= 13 
maxTS-2						INTEGER ::= 12
maxTS-LCR					INTEGER ::= 6
maxTS-LCR-1					INTEGER ::= 5 
maxURA						INTEGER ::= 8
maxURNTI-Group				INTEGER ::= 8

END
